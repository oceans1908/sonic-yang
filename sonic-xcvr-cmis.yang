module sonic-xcvr-cmis {
    namespace "http://github.com/Azure/sonic-xcvr-cmis";
    prefix xcvr-cmis;

    import sonic-common {
        prefix scommon;
    }

    import sonic-extension {
        prefix sonic-ext;
    }

    organization
        "SONiC";

    contact
        "SONiC";

    description
        "SONIC YANG for CMIS transceiver controls";

    revision 2024-03-15 {
        description
            "Initial commit";
    }

    container sonic-xcvr-cmis {
        container TRANSCEIVER_CMIS {
            list TRANSCEIVER_CMIS_LIST {
                key "ifname";

                leaf ifname {
                    type string {
                        pattern "Ethernet([1-3][0-9]{3}|[1-9][0-9]{2}|[1-9][0-9]|[0-9])|Eth([1-9]/(([1-9][0-9]{0,})|(([1-9][0-9]{0,})/([1-9][0-9]{0,}))))" {
                            error-message "Invalid interface name";
                            error-app-tag interface-name-invalid;
                        }
                    }
                }

                leaf laser_output_power {
                    type string;
                }
                leaf laser_output_power_lane0 {
                    type string;
                }
                leaf laser_output_power_lane1 {
                    type string;
                }
                leaf laser_output_power_lane2 {
                    type string;
                }
                leaf laser_output_power_lane3 {
                    type string;
                }
                leaf laser_output_power_lane4 {
                    type string;
                }
                leaf laser_output_power_lane5 {
                    type string;
                }
                leaf laser_output_power_lane6 {
                    type string;
                }
                leaf laser_output_power_lane7 {
                    type string;
                }
                leaf laser_grid_type {
                    type string;
                }
                leaf laser_grid_type_lane0 {
                    type string;
                }
                leaf laser_grid_type_lane1 {
                    type string;
                }
                leaf laser_grid_type_lane2 {
                    type string;
                }
                leaf laser_grid_type_lane3 {
                    type string;
                }
                leaf laser_grid_type_lane4 {
                    type string;
                }
                leaf laser_grid_type_lane5 {
                    type string;
                }
                leaf laser_grid_type_lane6 {
                    type string;
                }
                leaf laser_grid_type_lane7 {
                    type string;
                }
                leaf laser_grid_channel {
                    type string;
                }
                leaf laser_grid_channel_lane0 {
                    type string;
                }
                leaf laser_grid_channel_lane1 {
                    type string;
                }
                leaf laser_grid_channel_lane2 {
                    type string;
                }
                leaf laser_grid_channel_lane3 {
                    type string;
                }
                leaf laser_grid_channel_lane4 {
                    type string;
                }
                leaf laser_grid_channel_lane5 {
                    type string;
                }
                leaf laser_grid_channel_lane6 {
                    type string;
                }
                leaf laser_grid_channel_lane7 {
                    type string;
                }
                leaf laser_fine_tuning {
                    type string;
                }
                leaf laser_fine_tuning_lane0 {
                    type string;
                }
                leaf laser_fine_tuning_lane1 {
                    type string;
                }
                leaf laser_fine_tuning_lane2 {
                    type string;
                }
                leaf laser_fine_tuning_lane3 {
                    type string;
                }
                leaf laser_fine_tuning_lane4 {
                    type string;
                }
                leaf laser_fine_tuning_lane5 {
                    type string;
                }
                leaf laser_fine_tuning_lane6 {
                    type string;
                }
                leaf laser_fine_tuning_lane7 {
                    type string;
                }
            }
        }
    }
}
