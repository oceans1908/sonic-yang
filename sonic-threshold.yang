module sonic-threshold {
    namespace "http://github.com/Azure/sonic-threshold";
    prefix threshold;
    yang-version 1.1;

    import sonic-port {
        prefix prt;
    }

    import sonic-extension {
        prefix sonic-ext;
    }

    organization
        "SONiC";

    contact
        "SONiC";

    description
        "This module allows configuration of a threshold on supported buffers.
        The feature tracks ingress and egress buffer threshold breaches and notify
        network congestion event in real-time.";

    revision 2020-05-28 {
        description
            "Initial revision.";

    }

    container sonic-threshold {

        container THRESHOLD_TABLE {
            description
                "Configuration of a threshold on supported buffers in ingress and egress.";

            list THRESHOLD_TABLE_LIST {
                key "buffer threshold_buffer_type interface_name buffer_index_per_port";

                leaf buffer {
                    type enumeration {
                        enum priority-group;
                        enum queue;
                    }
                    description
                        "Configure buffer Threshold type as priority-group/queue.";
                }

                leaf threshold_buffer_type {
                    type enumeration {
                        enum shared;
                        enum headroom;
                        enum unicast;
                        enum multicast;
                    }
                    description
                        "Priority group/queue threshold buffer types.";
                }

                leaf interface_name {
                    type union {
                        type leafref {
                            path "/prt:sonic-port/prt:PORT/prt:PORT_LIST/prt:ifname";
                        }
                        type string {
                            pattern "CPU";
                        }
                    }
                    description
                        "Name of the interface for which priority-group/queue thresholds can be configured.";
                }

                leaf buffer_index_per_port {
                    type uint8;
                    description
                        "Priority group/queue index value.";
                    sonic-ext:custom-validation ValidateIndex;
                }

                leaf threshold {
                    type uint8 {
                        range "1..100" {
                            error-message "threshold value must be in range 1-100.";
                        }
                    }
                    description
                        "Threshold value for a specific buffer of an interface.";
                    sonic-ext:custom-validation ValidateThresholdSupport;
                }
            }
        }

        container THRESHOLD_BUFFERPOOL_TABLE {
            description
                "config db threshold bufferpool table";

            list THRESHOLD_BUFFERPOOL_TABLE_LIST {
                key "pool_name buffer-type";

                leaf pool_name {
                    type string;
                    description "Configure buffer pool name.";
                }

                leaf buffer-type {
                    type enumeration {
                        enum shared;
                        enum multicast;
                    }
                    description "buffer type";
                }

                leaf threshold {
                    type uint8 {
                        range "1..100" {
                            error-message "threshold value must be in range 1-100.";
                        }
                    }
                    description "Buffer pool threshold value.";
                    sonic-ext:custom-validation ValidateThresholdSupport;
                }
            }
        }

        container THRESHOLD_BUFFERPOOL_INTERFACE_TABLE {
            description
                "Threshold Bufferpool Interface table";

            list THRESHOLD_BUFFERPOOL_INTERFACE_TABLE_LIST {
                key "pool-name interface-name buffer-type";

                leaf pool-name {
                    type string;
                    description "Configure buffer pool name.";
                }

                leaf interface-name {
                    type leafref {
                        path "/prt:sonic-port/prt:PORT/prt:PORT_LIST/prt:ifname";
                    }
                    description
                        "Name of the interface for which bufferpool threshold can be configured.";
                }

                leaf buffer-type {
                    type enumeration {
                        enum shared;
                        enum unicast;
                    }
                    description "buffer type";
                }

                leaf threshold {
                    type uint8 {
                        range "1..100" {
                            error-message "threshold value must be in range 1-100.";
                        }
                    }
                    description "Buffer pool threshold value.";
                    sonic-ext:custom-validation ValidateThresholdSupport;
                }
            }
        }

        container THRESHOLD_DEVICE_TABLE {
            description
                "Configuration of a threshold on device globally.";

            list THRESHOLD_DEVICE_TABLE_LIST {
                key "type";

                leaf type {
                    type enumeration {
                        enum global;
                    }
                    description "Device type";
                }

                leaf threshold {
                    type uint8 {
                        range "1..100" {
                            error-message "threshold value must be in range 1-100.";
                        }
                    }
                    description "Buffer pool threshold value.";
                    sonic-ext:custom-validation ValidateThresholdSupport;
                }
            }
        }

        container THRESHOLD_BREACH_TABLE {
            sonic-ext:db-name "COUNTERS_DB";
            sonic-ext:key-delim ":";

            config false;
            description "config db threshold breach table";

            list THRESHOLD_BREACH_TABLE_LIST {
                key "breachreport eventid";

                leaf breachreport {
                    type enumeration {
                        enum breach-report;
                    }
                    description "Breach report event";
                }

                leaf eventid {
                    type uint64;
                    description "Breach report event id.";
                }

                leaf buffer {
                    type string;
                    description "Threshold buffer.";
                }

                leaf type {
                    type enumeration {
                        enum shared;
                        enum headroom;
                        enum unicast;
                        enum multicast;
                        enum ingress;
                        enum egress;
                        enum egress-unicast;
                        enum egress-multicast;
                        enum device;
                    }
                    description "Threshold buffer types.";
                }

                leaf port {
                    type union {
                        type leafref {
                            path "/prt:sonic-port/prt:PORT/prt:PORT_LIST/prt:ifname";
                        }
                        type string {
                            pattern "CPU";
                        }
                    }
                    description
                        "Name of the interface for which priority-group/queue thresholds can be configured.";
                }

                leaf index {
                    type uint8;
                    description "Priority group/queue index value.";
                }

                leaf breach_value {
                    type uint8 {
                        range "1..100" {
                            error-message "breach value must be in range 1-100.";
                        }
                    }
                    description "Counter value in % at breach.";
                }

                leaf time-stamp {
                    type string {
                        pattern '\d{4}-\d{2}-\d{2}T\d{2}:\d{2}:\d{2}(\.\d+)?'
                        + '(Z|[\+\-]\d{2}:\d{2})';
                    }
                    description
                        "time-stamp of the event when the threshold breach occurred.";
                }
            }
        }
    }

    rpc clear-threshold-breach {
        input {
            leaf breach_event_id {
                type union {
                    type enumeration {
                        enum all;
                    }
                    type uint64;
                }
                description
                    "Input parameter breach event id - all or a evendId";
            }
        }

        output {
            leaf status {
                type int32;
                description
                    "The status of the operation execution request.";
            }

            leaf status-detail {
                type string;
                description
                    "The detailed status of the operation execution request.";
            }
        }
    }
}
