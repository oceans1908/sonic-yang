module sonic-counters {
    namespace "http://github.com/Azure/sonic-counters";
    prefix scnts;

    import sonic-common {
        prefix scommon;
    }
    import ietf-yang-types {
        prefix ietf-yang;
    }

    organization
        "SONiC";

    contact
        "SONiC";

    description
        "SONIC COUNTERS";

    revision 2020-06-20 {
        description
            "Adding RPC for clear relay statistics.";
    }

    revision 2020-05-19 {
        description
            "Initial revision.";
    }

    rpc interface_counters {
        description "RPC to get interface counters.";
        output {
            leaf status {
                type int32;
                description
                    "The status of the operation execution request.";
            }
            leaf status-detail {
                type string;
                description
                    "The detailed status of the operation execution request.";
            }

            container interfaces {
                list interface {
                    key "name";

                    leaf name {
                        type string;
                    }
                    container state {
                        leaf oper-status {
                            type string;
                        }
                        leaf rate-interval {
                            type uint16;
                        }
                        container counters {
                            leaf in-octets {
                                type uint64;
                            }
                            leaf in-pkts {
                                type uint64;
                            }
                            leaf in-discards {
                                type uint64;
                            }
                            leaf in-errors {
                                type uint64;
                            }
                            leaf in-oversize-frames {
                                type uint64;
                            }
                            leaf in-octets-per-second {
                                type decimal64 {
                                    fraction-digits 2;
                                }
                            }
                            leaf in-pkts-per-second {
                                type decimal64 {
                                    fraction-digits 2;
                                }
                            }
                            leaf in-bits-per-second {
                                type decimal64 {
                                    fraction-digits 2;
                                }
                            }
                            leaf in-utilization {
                                type scommon:percentage;
                            }
                            leaf out-octets {
                                type uint64;
                            }
                            leaf out-pkts {
                                type uint64;
                            }
                            leaf out-discards {
                                type uint64;
                            }
                            leaf out-errors {
                                type uint64;
                            }
                            leaf out-oversize-frames {
                                type uint64;
                            }
                            leaf out-octets-per-second {
                                type decimal64 {
                                    fraction-digits 2;
                                }
                            }
                            leaf out-pkts-per-second {
                                type decimal64 {
                                    fraction-digits 2;
                                }
                            }
                            leaf out-bits-per-second {
                                type decimal64 {
                                    fraction-digits 2;
                                }
                            }
                            leaf out-utilization {
                                type scommon:percentage;
                            }
                        }
                    }
                }
            }
        }
    }

    rpc get_ethernet_counters {
        description "RPC to get Ethernet counters.";
        output {
            leaf status {
                type int32;
                description
                    "The status of the operation execution request.";
            }
            leaf status-detail {
                type string;
                description
                    "The detailed status of the operation execution request.";
            }

            container interfaces {
                list interface {
                    key "name";

                    leaf name {
                        type string;
                    }
                    container state {
                        container counters {
                            leaf in-frames-64-octets {
                                type ietf-yang:counter64;
                            }
                            leaf in-frames-65-127-octets {
                                type ietf-yang:counter64;
                            }
                            leaf in-frames-128-255-octets {
                                type ietf-yang:counter64;
                            }
                            leaf in-frames-256-511-octets {
                                type ietf-yang:counter64;
                            }
                            leaf in-frames-512-1023-octets {
                                type ietf-yang:counter64;
                            }
                            leaf in-frames-1024-1518-octets {
                                type ietf-yang:counter64;
                            }
                            leaf in-frames-1519-2047-octets {
                                type ietf-yang:counter64;
                            }
                            leaf in-frames-2048-4095-octets {
                                type ietf-yang:counter64;
                            }
                            leaf in-frames-4096-9216-octets {
                                type ietf-yang:counter64;
                            }
                            leaf in-frames-9217-16383-octets {
                                type ietf-yang:counter64;
                            }
                            leaf in-pkts {
                                type ietf-yang:counter64;
                            }
                            leaf in-unicast-pkts {
                                type ietf-yang:counter64;
                            }
                            leaf in-multicast-pkts {
                                type ietf-yang:counter64;
                            }
                            leaf in-broadcast-pkts {
                                type ietf-yang:counter64;
                            }
                            leaf in-jabber-frames {
                                type ietf-yang:counter64;
                            }
                            leaf in-fragment-frames {
                                type ietf-yang:counter64;
                            }
                            leaf in-undersize-frames {
                                type ietf-yang:counter64;
                            }
                            leaf in-oversize-frames {
                                type ietf-yang:counter64;
                            }
                            leaf in-crc-errors {
                                type ietf-yang:counter64;
                            }
                            leaf out-frames-64-octets {
                                type ietf-yang:counter64;
                            }
                            leaf out-frames-65-127-octets {
                                type ietf-yang:counter64;
                            }
                            leaf out-frames-128-255-octets {
                                type ietf-yang:counter64;
                            }
                            leaf out-frames-256-511-octets {
                                type ietf-yang:counter64;
                            }
                            leaf out-frames-512-1023-octets {
                                type ietf-yang:counter64;
                            }
                            leaf out-frames-1024-1518-octets {
                                type ietf-yang:counter64;
                            }
                            leaf out-frames-1519-2047-octets {
                                type ietf-yang:counter64;
                            }
                            leaf out-frames-2048-4095-octets {
                                type ietf-yang:counter64;
                            }
                            leaf out-frames-4096-9216-octets {
                                type ietf-yang:counter64;
                            }
                            leaf out-frames-9217-16383-octets {
                                type ietf-yang:counter64;
                            }
                            leaf out-pkts {
                                type ietf-yang:counter64;
                            }
                            leaf out-unicast-pkts {
                                type ietf-yang:counter64;
                            }
                            leaf out-multicast-pkts {
                                type ietf-yang:counter64;
                            }
                            leaf out-broadcast-pkts {
                                type ietf-yang:counter64;
                            }
                            leaf last-clear {
                                type scommon:timeticks64;
                            }
                        }
                    }
                }
            }
        }
    }
    rpc get_portchannel_counters {
        description "RPC to get PortChannel counters.";
        output {
            leaf status {
                type int32;
                description
                    "The status of the operation execution request.";
            }
            leaf status-detail {
                type string;
                description
                    "The detailed status of the operation execution request.";
            }
            container interfaces {
                list interface {
                    key "name";

                    leaf name {
                        type string;
                    }
                    container state {
                        container counters {
                            leaf in-pkts {
                                type ietf-yang:counter64;
                            }
                            leaf in-unicast-pkts {
                                type ietf-yang:counter64;
                            }
                            leaf in-multicast-pkts {
                                type ietf-yang:counter64;
                            }
                            leaf in-broadcast-pkts {
                                type ietf-yang:counter64;
                            }
                            leaf out-pkts {
                                type ietf-yang:counter64;
                            }
                            leaf out-unicast-pkts {
                                type ietf-yang:counter64;
                            }
                            leaf out-multicast-pkts {
                                type ietf-yang:counter64;
                            }
                            leaf out-broadcast-pkts {
                                type ietf-yang:counter64;
                            }
                            leaf last-clear {
                                type scommon:timeticks64;
                            }
                        }
                    }
                }
            }
        }
    }

    rpc clear_relay_counters {
        input {
            leaf ipv4-relay-param {
                type string;
                description
                    "Parameter for clearing ipv4 interface statistics";
            }
            leaf ipv6-relay-param {
                type string;
                description
                    "Parameter for clearing ipv6 interface statistics";
            }
        }
        output {
            leaf status {
                type string;
                description
                    " Success / Failure of clearing of dhcp relay statistics";
            }
        }
    }

    rpc rif_counters {
        description "RPC to get routing interface counters.";
    input {
        leaf riface {
            type string;
            description
                "Shows counters for given routing iface name. if routing iface is not present, the default all is used";
        }
    }

        output {
            leaf status {
                type int32;
                description
                    "The status of the operation execution request.";
            }
            leaf status-detail {
                type string;
                description
                    "The detailed status of the operation execution request.";
            }

            container rifs {
                list rif {
                    key "name";

                    leaf name {
                        type string;
                    }
                    container state {
                        leaf oper-status {
                            type string;
                        }
                        leaf rate-interval {
                            type uint16;
                        }
                        container counters {
                            leaf in-octets {
                                type uint64;
                            }
                            leaf in-pkts {
                                type uint64;
                            }
                            leaf in-discards {
                                type uint64;
                            }
                            leaf in-errors {
                                type uint64;
                            }
                            leaf in-oversize-frames {
                                type uint64;
                            }
                            leaf in-octets-per-second {
                                type decimal64 {
                                    fraction-digits 2;
                                }
                            }
                            leaf in-pkts-per-second {
                                type decimal64 {
                                    fraction-digits 2;
                                }
                            }
                            leaf in-bits-per-second {
                                type decimal64 {
                                    fraction-digits 2;
                                }
                            }
                            leaf in-utilization {
                                type scommon:percentage;
                            }
                            leaf out-octets {
                                type uint64;
                            }
                            leaf out-pkts {
                                type uint64;
                            }
                            leaf out-discards {
                                type uint64;
                            }
                            leaf out-errors {
                                type uint64;
                            }
                            leaf out-oversize-frames {
                                type uint64;
                            }
                            leaf out-octets-per-second {
                                type decimal64 {
                                    fraction-digits 2;
                                }
                            }
                            leaf out-pkts-per-second {
                                type decimal64 {
                                    fraction-digits 2;
                                }
                            }
                            leaf out-bits-per-second {
                                type decimal64 {
                                    fraction-digits 2;
                                }
                            }
                            leaf out-utilization {
                                type scommon:percentage;
                            }
                        }
                    }
                }
            }
        }
    }

    rpc clear_rif_counters {
        input {
            leaf rif {
                type string;
                description
                    "Parameter for clearing rif statistics";
            }
        }
        output {
            leaf status {
                type string;
                description
                    " Success / Failure of clearing rif statistics";
            }
        }
    }

    rpc vxlan_tunnel_counters {
        description "RPC to get VXLAN Tunnel counters.";
    input {
        leaf vxlan_tunnel_iface {
            type string;
            description
                "Shows counters for given VXLAN Tunnel . if vxlan_tunnel_iface is not present, the default all is used";
        }
    }

        output {
            leaf status {
                type int32;
                description
                    "The status of the operation execution request.";
            }
            leaf status-detail {
                type string;
                description
                    "The detailed status of the operation execution request.";
            }

            container interfaces {
                list interface {
                    key "name";

                    leaf name {
                        type string;
                    }
                    container state {
                        leaf oper-status {
                            type string;
                        }
                        leaf rate-interval {
                            type uint16;
                        }
                        container counters {
                            leaf in-octets {
                                type uint64;
                            }
                            leaf in-pkts {
                                type uint64;
                            }
                            leaf in-discards {
                                type uint64;
                            }
                            leaf in-errors {
                                type uint64;
                            }
                            leaf in-oversize-frames {
                                type uint64;
                            }
                            leaf in-octets-per-second {
                                type decimal64 {
                                    fraction-digits 2;
                                }
                            }
                            leaf in-pkts-per-second {
                                type decimal64 {
                                    fraction-digits 2;
                                }
                            }
                            leaf in-bits-per-second {
                                type decimal64 {
                                    fraction-digits 2;
                                }
                            }
                            leaf in-utilization {
                                type scommon:percentage;
                            }
                            leaf out-octets {
                                type uint64;
                            }
                            leaf out-pkts {
                                type uint64;
                            }
                            leaf out-discards {
                                type uint64;
                            }
                            leaf out-errors {
                                type uint64;
                            }
                            leaf out-oversize-frames {
                                type uint64;
                            }
                            leaf out-octets-per-second {
                                type decimal64 {
                                    fraction-digits 2;
                                }
                            }
                            leaf out-pkts-per-second {
                                type decimal64 {
                                    fraction-digits 2;
                                }
                            }
                            leaf out-bits-per-second {
                                type decimal64 {
                                    fraction-digits 2;
                                }
                            }
                            leaf out-utilization {
                                type scommon:percentage;
                            }
                        }
                    }
                }
            }
        }
    }

    rpc clear_vxlan_tunnel_counters {
        input {
            leaf vxlan_tunnel_iface {
                type string;
                description
                    "Parameter for clearing VXLAN statistics";
            }
        }
        output {
            leaf status {
                type string;
                description
                    " Success / Failure of clearing VXLAN statistics";
            }
        }
    }

    rpc drop_counters {
        description "RPC to get interface drop counters.";
        input {
            leaf iface {
                type string;
                description
                    "Shows counters for given iface name. if iface is not present, the default all is used";
            }
        }

        output {
            leaf status {
                type int32;
                description
                    "The status of the operation execution request.";
            }
            leaf status-detail {
                type string;
                description
                    "The detailed status of the operation execution request.";
            }

            container interfaces {
                list interface {
                    key "name";

                    leaf name {
                        type string;
                    }
                    container state {
                        leaf oper-status {
                            type string;
                        }
                        container counters {
                            leaf in-discards {
                                type uint64;
                            }
                            leaf in-errors {
                                type uint64;
                            }
                            leaf out-discards {
                                type uint64;
                            }
                            leaf out-errors {
                                type uint64;
                            }
                            leaf counter0-name {
                                type string;
                            }
                            leaf counter0-value {
                                type uint64;
                            }
                            leaf counter1-name {
                                type string;
                            }
                            leaf counter1-value {
                                type uint64;
                            }
                            leaf counter2-name {
                                type string;
                            }
                            leaf counter2-value {
                                type uint64;
                            }
                            leaf counter3-name {
                                type string;
                            }
                            leaf counter3-value {
                                type uint64;
                            }
                            leaf counter4-name {
                                type string;
                            }
                            leaf counter4-value {
                                type uint64;
                            }
                            leaf counter5-name {
                                type string;
                            }
                            leaf counter5-value {
                                type uint64;
                            }
                            leaf counter6-name {
                                type string;
                            }
                            leaf counter6-value {
                                type uint64;
                            }
                            leaf counter7-name {
                                type string;
                            }
                            leaf counter7-value {
                                type uint64;
                            }
                        }
                    }
                }
            }
        }
    }

    container sonic-counters {
        container FLEX_COUNTER_TABLE {
    
            list FLEX_COUNTER_TABLE_LIST { 
                key "id";
                    leaf id {
                        type enumeration {
                             enum PFCWD;
                             enum PORT;
                             enum QUEUE;
                             enum TUNNEL;
                             enum PHY;
                             enum RIF;
                             enum BUFFER_POOL_WATERMARK;
                             enum QUEUE_WATERMARK;
                             enum PG_WATERMARK;
                        }
                        description
                            "Flex Counter type";
                    }
                    leaf FLEX_COUNTER_STATUS {
                        type scommon:mode-enable;
                        default enable;
                        description
                            "Flex Counter enable or disable";
                    }
                    leaf POLL_INTERVAL {
                        type uint32;
                        description
                            "polling interval in msec";
                    }
               }
        }
    }

    rpc flf_counters {
        description "RPC to get FLF interface counters.";
        input {
            leaf fiface {
                type string;
                description
                    "Shows counters for given physical iface name. if physical iface is not present, the default all is used";
            }
        }

        output {
            leaf status {
                type int32;
                description
                    "The status of the operation execution request.";
            }
            leaf status-detail {
                type string;
                description
                    "The detailed status of the operation execution request.";
            }

            container flfs {
                list flf {
                    key "name";

                    leaf name {
                        type string;
                    }
                    container state {
                        leaf oper-status {
                            type string;
                        }
                        container counters {
                            leaf hw-protection-switchover-events {
                                type uint64;
                            }
                            leaf hw-protection-switchover-drop-pkts {
                                type uint64;
                            }
                        }
                    }
                }
            }
        }
    }

}
