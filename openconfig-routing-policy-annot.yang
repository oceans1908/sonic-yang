module openconfig-routing-policy-annot {

    yang-version "1";

    namespace "http://openconfig.net/yang/annotation/oc-rpol-annot";
    prefix "oc-rpol-annot";

    import openconfig-routing-policy { prefix oc-rpol; }
    import openconfig-routing-policy-ext { prefix oc-rpol-ext; }
    import openconfig-bgp-policy { prefix oc-bgp-pol; }
    import openconfig-bgp-policy-ext { prefix oc-bgp-pol-ext; }
    import sonic-extensions {prefix sonic-ext; }

    deviation /oc-rpol:routing-policy {
        deviate add {
            sonic-ext:user-role-priv "write:netadmin";
        }
    }

    deviation /oc-rpol:routing-policy/oc-rpol:policy-definitions {
        deviate add {
            sonic-ext:table-name "NONE";
        }
    }

    deviation /oc-rpol:routing-policy/oc-rpol:policy-definitions/oc-rpol:policy-definition {
        deviate add {
            sonic-ext:table-name "ROUTE_MAP_SET";
            sonic-ext:path-transformer "route_map_path_xfmr";
        }
    }

    deviation /oc-rpol:routing-policy/oc-rpol:policy-definitions/oc-rpol:policy-definition/oc-rpol:name {
      deviate add {
            sonic-ext:field-transformer "route_map_field_xfmr";
      }
    }

    deviation /oc-rpol:routing-policy/oc-rpol:policy-definitions/oc-rpol:policy-definition/oc-rpol:config/oc-rpol:name {
      deviate add {
            sonic-ext:field-transformer "route_map_field_xfmr";
      }
    }

    deviation /oc-rpol:routing-policy/oc-rpol:policy-definitions/oc-rpol:policy-definition/oc-rpol:state/oc-rpol:name {
      deviate add {
            sonic-ext:field-transformer "route_map_field_xfmr";
      }
    }

    deviation /oc-rpol:routing-policy/oc-rpol:policy-definitions/oc-rpol:policy-definition/oc-rpol:statements {
      deviate add {
            sonic-ext:table-name "NONE";
      }
    }

    deviation /oc-rpol:routing-policy/oc-rpol:policy-definitions/oc-rpol:policy-definition/oc-rpol:statements/oc-rpol:statement {
      deviate add {
            sonic-ext:table-name "ROUTE_MAP";
            sonic-ext:key-transformer "route_map_key_xfmr";
      }
    }

    deviation /oc-rpol:routing-policy/oc-rpol:policy-definitions/oc-rpol:policy-definition/oc-rpol:statements/oc-rpol:statement/oc-rpol:name {
      deviate add {
            sonic-ext:field-transformer "route_map_stmt_field_xfmr";
      }
    }

    deviation /oc-rpol:routing-policy/oc-rpol:policy-definitions/oc-rpol:policy-definition/oc-rpol:statements/oc-rpol:statement/oc-rpol:config/oc-rpol:name {
      deviate add {
            sonic-ext:field-transformer "route_map_stmt_field_xfmr";
      }
    }

    deviation /oc-rpol:routing-policy/oc-rpol:policy-definitions/oc-rpol:policy-definition/oc-rpol:statements/oc-rpol:statement/oc-rpol:state/oc-rpol:name {
      deviate add {
            sonic-ext:field-transformer "route_map_stmt_field_xfmr";
      }
    }

    deviation /oc-rpol:routing-policy/oc-rpol:policy-definitions/oc-rpol:policy-definition/oc-rpol:statements/oc-rpol:statement/oc-rpol:actions/oc-rpol:config/oc-rpol:policy-result {
      deviate add {
            sonic-ext:field-transformer "route_map_action_policy_result_xfmr";
            sonic-ext:field-name "route_operation";
      }
    }

    deviation /oc-rpol:routing-policy/oc-rpol:policy-definitions/oc-rpol:policy-definition/oc-rpol:statements/oc-rpol:statement/oc-rpol:actions/oc-rpol:state/oc-rpol:policy-result {
      deviate add {
            sonic-ext:field-transformer "route_map_action_policy_result_xfmr";
            sonic-ext:field-name "route_operation";
      }
    }

    deviation /oc-rpol:routing-policy/oc-rpol:policy-definitions/oc-rpol:policy-definition/oc-rpol:statements/oc-rpol:statement/oc-rpol:conditions/oc-rpol:config/oc-rpol:install-protocol-eq {
      deviate add {
            sonic-ext:field-transformer "route_map_match_protocol_xfmr";
            sonic-ext:field-name "match_protocol";
      }
    }

    deviation /oc-rpol:routing-policy/oc-rpol:policy-definitions/oc-rpol:policy-definition/oc-rpol:statements/oc-rpol:statement/oc-rpol:conditions/oc-rpol:state/oc-rpol:install-protocol-eq {
      deviate add {
            sonic-ext:field-transformer "route_map_match_protocol_xfmr";
            sonic-ext:field-name "match_protocol";
      }
    }

    deviation /oc-rpol:routing-policy/oc-rpol:policy-definitions/oc-rpol:policy-definition/oc-rpol:statements/oc-rpol:statement/oc-rpol:conditions/oc-rpol:match-prefix-set/oc-rpol:config/oc-rpol:match-set-options {
      deviate add {
            sonic-ext:field-transformer "route_map_match_set_options_restrict_type_xfmr";
      }
    }

    deviation /oc-rpol:routing-policy/oc-rpol:policy-definitions/oc-rpol:policy-definition/oc-rpol:statements/oc-rpol:statement/oc-rpol:conditions/oc-rpol:match-prefix-set/oc-rpol:config/oc-rpol:prefix-set {
      deviate add {
            sonic-ext:field-name "match_prefix_set";
      }
    }

    deviation /oc-rpol:routing-policy/oc-rpol:policy-definitions/oc-rpol:policy-definition/oc-rpol:statements/oc-rpol:statement/oc-rpol:conditions/oc-rpol:match-prefix-set/oc-rpol:config/oc-rpol-ext:ipv6-prefix-set {
      deviate add {
            sonic-ext:field-name "match_ipv6_prefix_set";
      }
    }

    deviation /oc-rpol:routing-policy/oc-rpol:policy-definitions/oc-rpol:policy-definition/oc-rpol:statements/oc-rpol:statement/oc-rpol:conditions/oc-bgp-pol:bgp-conditions/oc-bgp-pol:config/oc-bgp-pol-ext:next-hop-set {
      deviate add {
            sonic-ext:field-name "match_next_hop_set";
      }
    }

    deviation /oc-rpol:routing-policy/oc-rpol:policy-definitions/oc-rpol:policy-definition/oc-rpol:statements/oc-rpol:statement/oc-rpol:conditions/oc-bgp-pol:bgp-conditions/oc-bgp-pol:state/oc-bgp-pol-ext:next-hop-set {
      deviate add {
            sonic-ext:field-name "match_next_hop_set";
      }
    }

    deviation /oc-rpol:routing-policy/oc-rpol:policy-definitions/oc-rpol:policy-definition/oc-rpol:statements/oc-rpol:statement/oc-rpol:conditions/oc-rpol:match-prefix-set/oc-rpol:state/oc-rpol:match-set-options {
      deviate add {
            sonic-ext:field-transformer "route_map_match_set_options_restrict_type_xfmr";
      }
    }

    deviation /oc-rpol:routing-policy/oc-rpol:policy-definitions/oc-rpol:policy-definition/oc-rpol:statements/oc-rpol:statement/oc-rpol:conditions/oc-rpol:match-prefix-set/oc-rpol:state/oc-rpol:prefix-set {
      deviate add {
            sonic-ext:field-name "match_prefix_set";
      }
    }

    deviation /oc-rpol:routing-policy/oc-rpol:policy-definitions/oc-rpol:policy-definition/oc-rpol:statements/oc-rpol:statement/oc-rpol:conditions/oc-rpol:match-prefix-set/oc-rpol:state/oc-rpol-ext:ipv6-prefix-set {
      deviate add {
            sonic-ext:field-name "match_ipv6_prefix_set";
      }
    }

    deviation /oc-rpol:routing-policy/oc-rpol:policy-definitions/oc-rpol:policy-definition/oc-rpol:statements/oc-rpol:statement/oc-rpol:conditions/oc-rpol:match-interface/oc-rpol:config/oc-rpol:interface {
      deviate add {
            sonic-ext:field-name "match_interface";
      }
    }


    deviation /oc-rpol:routing-policy/oc-rpol:policy-definitions/oc-rpol:policy-definition/oc-rpol:statements/oc-rpol:statement/oc-rpol:conditions/oc-rpol:match-interface/oc-rpol:state/oc-rpol:interface {
      deviate add {
            sonic-ext:field-name "match_interface";
      }
    }

    deviation /oc-rpol:routing-policy/oc-rpol:policy-definitions/oc-rpol:policy-definition/oc-rpol:statements/oc-rpol:statement/oc-rpol:conditions/oc-rpol:match-neighbor-set/oc-rpol:config/oc-rpol-ext:address {
      deviate add {
            sonic-ext:field-name "match_neighbor";
      }
    }

    deviation /oc-rpol:routing-policy/oc-rpol:policy-definitions/oc-rpol:policy-definition/oc-rpol:statements/oc-rpol:statement/oc-rpol:conditions/oc-rpol:match-neighbor-set/oc-rpol:state/oc-rpol-ext:address {
      deviate add {
            sonic-ext:field-name "match_neighbor";
      }
    }

    deviation /oc-rpol:routing-policy/oc-rpol:policy-definitions/oc-rpol:policy-definition/oc-rpol:statements/oc-rpol:statement/oc-rpol:conditions/oc-rpol:match-tag-set/oc-rpol:config/oc-rpol-ext:tag-value {
      deviate add {
            sonic-ext:field-name "match_tag";
      }
    }

    deviation /oc-rpol:routing-policy/oc-rpol:policy-definitions/oc-rpol:policy-definition/oc-rpol:statements/oc-rpol:statement/oc-rpol:conditions/oc-rpol:match-tag-set/oc-rpol:state/oc-rpol-ext:tag-value {
      deviate add {
            sonic-ext:field-name "match_tag";
      }
    }

    deviation /oc-rpol:routing-policy/oc-rpol:policy-definitions/oc-rpol:policy-definition/oc-rpol:statements/oc-rpol:statement/oc-rpol:conditions/oc-rpol-ext:match-src-network-instance/oc-rpol-ext:config/oc-rpol-ext:name {
      deviate add {
            sonic-ext:field-name "match_src_vrf";
      }
    }

    deviation /oc-rpol:routing-policy/oc-rpol:policy-definitions/oc-rpol:policy-definition/oc-rpol:statements/oc-rpol:statement/oc-rpol:conditions/oc-rpol-ext:match-src-network-instance/oc-rpol-ext:state/oc-rpol-ext:name {
      deviate add {
            sonic-ext:field-name "match_src_vrf";
      }
    }

    deviation /oc-rpol:routing-policy/oc-rpol:policy-definitions/oc-rpol:policy-definition/oc-rpol:statements/oc-rpol:statement/oc-rpol:conditions/oc-rpol:config/oc-rpol:call-policy {
      deviate add {
            sonic-ext:field-name "call_route_map";
      }
    }

    deviation /oc-rpol:routing-policy/oc-rpol:policy-definitions/oc-rpol:policy-definition/oc-rpol:statements/oc-rpol:statement/oc-rpol:conditions/oc-rpol:state/oc-rpol:call-policy {
      deviate add {
            sonic-ext:field-name "call_route_map";
      }
    }

    deviation /oc-rpol:routing-policy/oc-rpol:policy-definitions/oc-rpol:policy-definition/oc-rpol:statements/oc-rpol:statement/oc-rpol:conditions/oc-bgp-pol:bgp-conditions/oc-bgp-pol:config/oc-bgp-pol:med-eq {
      deviate add {
            sonic-ext:field-name "match_med";
      }
    }

    deviation /oc-rpol:routing-policy/oc-rpol:policy-definitions/oc-rpol:policy-definition/oc-rpol:statements/oc-rpol:statement/oc-rpol:conditions/oc-bgp-pol:bgp-conditions/oc-bgp-pol:config/oc-bgp-pol:origin-eq {
      deviate add {
            sonic-ext:field-name "match_origin";
      }
    }

    deviation /oc-rpol:routing-policy/oc-rpol:policy-definitions/oc-rpol:policy-definition/oc-rpol:statements/oc-rpol:statement/oc-rpol:conditions/oc-bgp-pol:bgp-conditions/oc-bgp-pol:config/oc-bgp-pol:local-pref-eq {
      deviate add {
            sonic-ext:field-name "match_local_pref";
      }
    }
    
    deviation /oc-rpol:routing-policy/oc-rpol:policy-definitions/oc-rpol:policy-definition/oc-rpol:statements/oc-rpol:statement/oc-rpol:conditions/oc-bgp-pol:bgp-conditions/oc-bgp-pol-ext:match-evpn-set/oc-bgp-pol-ext:config/oc-bgp-pol-ext:vni-number {
      deviate add {
            sonic-ext:field-name "match_evpn_vni_number";
      }
    }

    deviation /oc-rpol:routing-policy/oc-rpol:policy-definitions/oc-rpol:policy-definition/oc-rpol:statements/oc-rpol:statement/oc-rpol:conditions/oc-bgp-pol:bgp-conditions/oc-bgp-pol-ext:match-evpn-set/oc-bgp-pol-ext:config/oc-bgp-pol-ext:default-type5-route {
      deviate add {
            sonic-ext:field-name "match_evpn_default_type5_route";
      }
    }

    deviation /oc-rpol:routing-policy/oc-rpol:policy-definitions/oc-rpol:policy-definition/oc-rpol:statements/oc-rpol:statement/oc-rpol:conditions/oc-bgp-pol:bgp-conditions/oc-bgp-pol-ext:match-evpn-set/oc-bgp-pol-ext:config/oc-bgp-pol-ext:route-type {
      deviate add {
            sonic-ext:field-name "match_evpn_advertise_route_type";
      }
    }

    deviation /oc-rpol:routing-policy/oc-rpol:policy-definitions/oc-rpol:policy-definition/oc-rpol:statements/oc-rpol:statement/oc-rpol:conditions/oc-bgp-pol:bgp-conditions/oc-bgp-pol-ext:match-evpn-set/oc-bgp-pol-ext:state/oc-bgp-pol-ext:vni-number {
      deviate add {
            sonic-ext:field-name "match_evpn_vni_number";
      }
    }

    deviation /oc-rpol:routing-policy/oc-rpol:policy-definitions/oc-rpol:policy-definition/oc-rpol:statements/oc-rpol:statement/oc-rpol:conditions/oc-bgp-pol:bgp-conditions/oc-bgp-pol-ext:match-evpn-set/oc-bgp-pol-ext:state/oc-bgp-pol-ext:default-type5-route {
      deviate add {
            sonic-ext:field-name "match_evpn_default_type5_route";
      }
    }

    deviation /oc-rpol:routing-policy/oc-rpol:policy-definitions/oc-rpol:policy-definition/oc-rpol:statements/oc-rpol:statement/oc-rpol:conditions/oc-bgp-pol:bgp-conditions/oc-bgp-pol-ext:match-evpn-set/oc-bgp-pol-ext:state/oc-bgp-pol-ext:route-type {
      deviate add {
            sonic-ext:field-name "match_evpn_advertise_route_type";
      }
    }

    deviation /oc-rpol:routing-policy/oc-rpol:policy-definitions/oc-rpol:policy-definition/oc-rpol:statements/oc-rpol:statement/oc-rpol:conditions/oc-bgp-pol:bgp-conditions/oc-bgp-pol:config/oc-bgp-pol:community-set {
      deviate add {
            sonic-ext:field-name "match_community";
      }
    }

    deviation /oc-rpol:routing-policy/oc-rpol:policy-definitions/oc-rpol:policy-definition/oc-rpol:statements/oc-rpol:statement/oc-rpol:conditions/oc-bgp-pol:bgp-conditions/oc-bgp-pol:config/oc-bgp-pol:ext-community-set {
      deviate add {
            sonic-ext:field-name "match_ext_community";
      }
    }

    deviation /oc-rpol:routing-policy/oc-rpol:policy-definitions/oc-rpol:policy-definition/oc-rpol:statements/oc-rpol:statement/oc-rpol:conditions/oc-bgp-pol:bgp-conditions/oc-bgp-pol:state/oc-bgp-pol:med-eq {
      deviate add {
            sonic-ext:field-name "match_med";
      }
    }

    deviation /oc-rpol:routing-policy/oc-rpol:policy-definitions/oc-rpol:policy-definition/oc-rpol:statements/oc-rpol:statement/oc-rpol:conditions/oc-bgp-pol:bgp-conditions/oc-bgp-pol:state/oc-bgp-pol:origin-eq {
      deviate add {
            sonic-ext:field-name "match_origin";
      }
    }

    deviation /oc-rpol:routing-policy/oc-rpol:policy-definitions/oc-rpol:policy-definition/oc-rpol:statements/oc-rpol:statement/oc-rpol:conditions/oc-bgp-pol:bgp-conditions/oc-bgp-pol:state/oc-bgp-pol:local-pref-eq {
      deviate add {
            sonic-ext:field-name "match_local_pref";
      }
    }

    deviation /oc-rpol:routing-policy/oc-rpol:policy-definitions/oc-rpol:policy-definition/oc-rpol:statements/oc-rpol:statement/oc-rpol:conditions/oc-bgp-pol:bgp-conditions/oc-bgp-pol:state/oc-bgp-pol:community-set {
      deviate add {
            sonic-ext:field-name "match_community";
      }
    }

    deviation /oc-rpol:routing-policy/oc-rpol:policy-definitions/oc-rpol:policy-definition/oc-rpol:statements/oc-rpol:statement/oc-rpol:conditions/oc-bgp-pol:bgp-conditions/oc-bgp-pol:state/oc-bgp-pol:ext-community-set {
      deviate add {
            sonic-ext:field-name "match_ext_community";
      }
    }

    deviation /oc-rpol:routing-policy/oc-rpol:policy-definitions/oc-rpol:policy-definition/oc-rpol:statements/oc-rpol:statement/oc-rpol:conditions/oc-bgp-pol:bgp-conditions/oc-bgp-pol:match-as-path-set/oc-bgp-pol:config/oc-bgp-pol:as-path-set {
      deviate add {
            sonic-ext:field-name "match_as_path";
      }
    }

    deviation /oc-rpol:routing-policy/oc-rpol:policy-definitions/oc-rpol:policy-definition/oc-rpol:statements/oc-rpol:statement/oc-rpol:conditions/oc-bgp-pol:bgp-conditions/oc-bgp-pol:match-as-path-set/oc-bgp-pol:config/oc-bgp-pol:match-set-options {
      deviate add {
            sonic-ext:field-transformer "route_map_match_set_options_xfmr";
      }
    }

    deviation /oc-rpol:routing-policy/oc-rpol:policy-definitions/oc-rpol:policy-definition/oc-rpol:statements/oc-rpol:statement/oc-rpol:conditions/oc-bgp-pol:bgp-conditions/oc-bgp-pol:match-as-path-set/oc-bgp-pol:state/oc-bgp-pol:as-path-set {
      deviate add {
            sonic-ext:field-name "match_as_path";
      }
    }

    deviation /oc-rpol:routing-policy/oc-rpol:policy-definitions/oc-rpol:policy-definition/oc-rpol:statements/oc-rpol:statement/oc-rpol:conditions/oc-bgp-pol:bgp-conditions/oc-bgp-pol:match-as-path-set/oc-bgp-pol:state/oc-bgp-pol:match-set-options {
      deviate add {
            sonic-ext:field-transformer "route_map_match_set_options_xfmr";
      }
    }

    deviation /oc-rpol:routing-policy/oc-rpol:policy-definitions/oc-rpol:policy-definition/oc-rpol:statements/oc-rpol:statement/oc-rpol:actions/oc-bgp-pol:bgp-actions/oc-bgp-pol:config/oc-bgp-pol:set-route-origin {
      deviate add {
            sonic-ext:field-name "set_origin";
      }
    }

    deviation /oc-rpol:routing-policy/oc-rpol:policy-definitions/oc-rpol:policy-definition/oc-rpol:statements/oc-rpol:statement/oc-rpol:actions/oc-bgp-pol:bgp-actions/oc-bgp-pol:config/oc-bgp-pol:set-local-pref {
      deviate add {
            sonic-ext:field-name "set_local_pref";
      }
    }

    deviation /oc-rpol:routing-policy/oc-rpol:policy-definitions/oc-rpol:policy-definition/oc-rpol:statements/oc-rpol:statement/oc-rpol:actions/oc-bgp-pol:bgp-actions/oc-bgp-pol:config/oc-bgp-pol:set-next-hop {
      deviate add {
            sonic-ext:field-transformer "route_map_set_next_hop_xfmr";
            sonic-ext:field-name "set_next_hop";
      }
    }

    deviation /oc-rpol:routing-policy/oc-rpol:policy-definitions/oc-rpol:policy-definition/oc-rpol:statements/oc-rpol:statement/oc-rpol:actions/oc-bgp-pol:bgp-actions/oc-rpol-ext:ars-object/oc-rpol-ext:config/oc-rpol-ext:set-ars-object {
      deviate add {
            sonic-ext:field-name "set_ars_object";
      }
    }

    deviation /oc-rpol:routing-policy/oc-rpol:policy-definitions/oc-rpol:policy-definition/oc-rpol:statements/oc-rpol:statement/oc-rpol:actions/oc-bgp-pol:bgp-actions/oc-rpol-ext:ars-object/oc-rpol-ext:state/oc-rpol-ext:set-ars-object {
      deviate add {
            sonic-ext:field-name "set_ars_object";
      }
    }

    deviation /oc-rpol:routing-policy/oc-rpol:policy-definitions/oc-rpol:policy-definition/oc-rpol:statements/oc-rpol:statement/oc-rpol:actions/oc-bgp-pol:bgp-actions/oc-bgp-pol:config/oc-bgp-pol:set-ipv6-next-hop-global {
      deviate add {
            sonic-ext:field-transformer "route_map_set_ipv6_next_hop_xfmr";
            sonic-ext:field-name "set_ipv6_next_hop_global";
      }
    }

    deviation /oc-rpol:routing-policy/oc-rpol:policy-definitions/oc-rpol:policy-definition/oc-rpol:statements/oc-rpol:statement/oc-rpol:actions/oc-bgp-pol:bgp-actions/oc-bgp-pol:config/oc-bgp-pol:set-ipv6-next-hop-prefer-global {
      deviate add {
            sonic-ext:field-name "set_ipv6_next_hop_prefer_global";
      }
    }

    deviation /oc-rpol:routing-policy/oc-rpol:policy-definitions/oc-rpol:policy-definition/oc-rpol:statements/oc-rpol:statement/oc-rpol:actions/oc-bgp-pol:bgp-actions/oc-bgp-pol:config/oc-bgp-pol-ext:set-next-hop-native {
      deviate add {
            sonic-ext:field-name "set_next_hop_native";
      }
    }

    deviation /oc-rpol:routing-policy/oc-rpol:policy-definitions/oc-rpol:policy-definition/oc-rpol:statements/oc-rpol:statement/oc-rpol:actions/oc-bgp-pol:bgp-actions/oc-bgp-pol:config/oc-bgp-pol-ext:set-ipv6-next-hop-native {
      deviate add {
            sonic-ext:field-name "set_ipv6_next_hop_native";
      }
    }           

    deviation /oc-rpol:routing-policy/oc-rpol:policy-definitions/oc-rpol:policy-definition/oc-rpol:statements/oc-rpol:statement/oc-rpol:actions/oc-bgp-pol:bgp-actions/oc-bgp-pol:config/oc-bgp-pol:set-med {
      deviate add {
            sonic-ext:field-transformer "route_map_set_med_xfmr";
            sonic-ext:field-name "set_med";
      }
    }

    deviation /oc-rpol:routing-policy/oc-rpol:policy-definitions/oc-rpol:policy-definition/oc-rpol:statements/oc-rpol:statement/oc-rpol:actions/oc-bgp-pol:bgp-actions/oc-bgp-pol:config/oc-bgp-pol:set-weight {
      deviate add {
            sonic-ext:field-name "set_weight";
      }
    }

    deviation /oc-rpol:routing-policy/oc-rpol:policy-definitions/oc-rpol:policy-definition/oc-rpol:statements/oc-rpol:statement/oc-rpol:actions/oc-bgp-pol:bgp-actions/oc-bgp-pol:config/oc-bgp-pol:set-tag {
      deviate add {
            sonic-ext:field-name "set_tag";
      }
    }

    deviation /oc-rpol:routing-policy/oc-rpol:policy-definitions/oc-rpol:policy-definition/oc-rpol:statements/oc-rpol:statement/oc-rpol:actions/oc-rpol:metric-action/oc-rpol:config/oc-rpol:action {
      deviate add {
            sonic-ext:field-name "set_metric_action";
      }
    }

    deviation /oc-rpol:routing-policy/oc-rpol:policy-definitions/oc-rpol:policy-definition/oc-rpol:statements/oc-rpol:statement/oc-rpol:actions/oc-rpol:metric-action/oc-rpol:config/oc-rpol:metric {
      deviate add {
            sonic-ext:field-name "set_metric";
      }
    }

    deviation /oc-rpol:routing-policy/oc-rpol:policy-definitions/oc-rpol:policy-definition/oc-rpol:statements/oc-rpol:statement/oc-rpol:actions/oc-rpol:metric-action/oc-rpol:state/oc-rpol:action {
      deviate add {
            sonic-ext:field-name "set_metric_action";
      }
    }

    deviation /oc-rpol:routing-policy/oc-rpol:policy-definitions/oc-rpol:policy-definition/oc-rpol:statements/oc-rpol:statement/oc-rpol:actions/oc-rpol:metric-action/oc-rpol:state/oc-rpol:metric {
      deviate add {
            sonic-ext:field-name "set_metric";
      }
    }

    deviation /oc-rpol:routing-policy/oc-rpol:policy-definitions/oc-rpol:policy-definition/oc-rpol:statements/oc-rpol:statement/oc-rpol:actions/oc-bgp-pol:bgp-actions/oc-bgp-pol:state/oc-bgp-pol:set-route-origin {
      deviate add {
            sonic-ext:field-name "set_origin";
      }
    }

    deviation /oc-rpol:routing-policy/oc-rpol:policy-definitions/oc-rpol:policy-definition/oc-rpol:statements/oc-rpol:statement/oc-rpol:actions/oc-bgp-pol:bgp-actions/oc-bgp-pol:state/oc-bgp-pol:set-local-pref {
      deviate add {
            sonic-ext:field-name "set_local_pref";
      }
    }

    deviation /oc-rpol:routing-policy/oc-rpol:policy-definitions/oc-rpol:policy-definition/oc-rpol:statements/oc-rpol:statement/oc-rpol:actions/oc-bgp-pol:bgp-actions/oc-bgp-pol:state/oc-bgp-pol:set-next-hop {
      deviate add {
            sonic-ext:field-name "set_next_hop";
      }
    }

    deviation /oc-rpol:routing-policy/oc-rpol:policy-definitions/oc-rpol:policy-definition/oc-rpol:statements/oc-rpol:statement/oc-rpol:actions/oc-bgp-pol:bgp-actions/oc-bgp-pol:state/oc-bgp-pol:set-ipv6-next-hop-global {
      deviate add {
            sonic-ext:field-transformer "route_map_set_ipv6_next_hop_xfmr";
            sonic-ext:field-name "set_ipv6_next_hop_global";
      }
    }

    deviation /oc-rpol:routing-policy/oc-rpol:policy-definitions/oc-rpol:policy-definition/oc-rpol:statements/oc-rpol:statement/oc-rpol:actions/oc-bgp-pol:bgp-actions/oc-bgp-pol:state/oc-bgp-pol:set-ipv6-next-hop-prefer-global {
      deviate add {
            sonic-ext:field-name "set_ipv6_next_hop_prefer_global";
      }
    }

    deviation /oc-rpol:routing-policy/oc-rpol:policy-definitions/oc-rpol:policy-definition/oc-rpol:statements/oc-rpol:statement/oc-rpol:actions/oc-bgp-pol:bgp-actions/oc-bgp-pol:state/oc-bgp-pol-ext:set-next-hop-native {
      deviate add {
            sonic-ext:field-name "set_next_hop_native";
      }
    }
    
    deviation /oc-rpol:routing-policy/oc-rpol:policy-definitions/oc-rpol:policy-definition/oc-rpol:statements/oc-rpol:statement/oc-rpol:actions/oc-bgp-pol:bgp-actions/oc-bgp-pol:state/oc-bgp-pol-ext:set-ipv6-next-hop-native {
      deviate add {
            sonic-ext:field-name "set_ipv6_next_hop_native";
      }
    }        

    deviation /oc-rpol:routing-policy/oc-rpol:policy-definitions/oc-rpol:policy-definition/oc-rpol:statements/oc-rpol:statement/oc-rpol:actions/oc-bgp-pol:bgp-actions/oc-bgp-pol:state/oc-bgp-pol:set-med {
      deviate add {
            sonic-ext:field-transformer "route_map_set_med_xfmr";
            sonic-ext:field-name "set_med";
      }
    }

    deviation /oc-rpol:routing-policy/oc-rpol:policy-definitions/oc-rpol:policy-definition/oc-rpol:statements/oc-rpol:statement/oc-rpol:actions/oc-bgp-pol:bgp-actions/oc-bgp-pol:state/oc-bgp-pol:set-weight {
      deviate add {
            sonic-ext:field-name "set_weight";
      }
    }

    deviation /oc-rpol:routing-policy/oc-rpol:policy-definitions/oc-rpol:policy-definition/oc-rpol:statements/oc-rpol:statement/oc-rpol:actions/oc-bgp-pol:bgp-actions/oc-bgp-pol:state/oc-bgp-pol:set-tag {
      deviate add {
            sonic-ext:field-name "set_tag";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:config/oc-bgp-pol:repeat-n {
      deviate add {
            sonic-ext:field-name "set_repeat_asn";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:config/oc-bgp-pol:asn {
      deviate add {
            sonic-ext:field-transformer "route_map_bgp_action_set_aspathprepend_fld_xfmr";
            sonic-ext:field-name "set_asn";
      }
    }

    deviation /oc-rpol:routing-policy/oc-rpol:policy-definitions/oc-rpol:policy-definition/oc-rpol:statements/oc-rpol:statement/oc-rpol:actions/oc-bgp-pol:bgp-actions/oc-bgp-pol:set-community-delete/oc-bgp-pol:config/oc-bgp-pol:community-set-delete {
      deviate add {
            sonic-ext:field-name "set_community_delete_ref";
      }
    }

    deviation /oc-rpol:routing-policy/oc-rpol:policy-definitions/oc-rpol:policy-definition/oc-rpol:statements/oc-rpol:statement/oc-rpol:actions/oc-bgp-pol:bgp-actions/oc-bgp-pol:set-community-delete/oc-bgp-pol:state/oc-bgp-pol:community-set-delete {
      deviate add {
            sonic-ext:field-name "set_community_delete_ref";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:config/oc-rpol-ext:asn-list {
       deviate add {
            sonic-ext:field-transformer "route_map_bgp_action_set_aspathprepend_list_fld_xfmr";
            sonic-ext:field-name "set_asn_list";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:state/oc-rpol-ext:asn-list {
       deviate add {
            sonic-ext:field-transformer "route_map_bgp_action_set_aspathprepend_list_fld_xfmr";
            sonic-ext:field-name "set_asn_list";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:state/oc-bgp-pol:repeat-n {
      deviate add {
            sonic-ext:field-name "set_repeat_asn";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:state/oc-bgp-pol:asn {
      deviate add {
            sonic-ext:field-transformer "route_map_bgp_action_set_aspathprepend_fld_xfmr";
            sonic-ext:field-name "set_asn";
      }
    }

    deviation /oc-rpol:routing-policy/oc-rpol:policy-definitions/oc-rpol:policy-definition/oc-rpol:statements/oc-rpol:statement/oc-rpol:actions/oc-bgp-pol:bgp-actions/oc-bgp-pol:set-community {
      deviate add {
          sonic-ext:subtree-transformer "route_map_bgp_action_set_community";          
      }
    }

    deviation /oc-rpol:routing-policy/oc-rpol:policy-definitions/oc-rpol:policy-definition/oc-rpol:statements/oc-rpol:statement/oc-rpol:actions/oc-bgp-pol:bgp-actions/oc-bgp-pol:set-ext-community {
      deviate add {
          sonic-ext:subtree-transformer "route_map_bgp_action_set_ext_community";          
      }
    }

   /* PREFIX SETS */
    deviation /oc-rpol:routing-policy/oc-rpol:defined-sets/oc-rpol:prefix-sets {
      deviate add {
        sonic-ext:table-name "NONE";
      }
    }

    deviation /oc-rpol:routing-policy/oc-rpol:defined-sets/oc-rpol:prefix-sets/oc-rpol:prefix-set {
      deviate add {
        sonic-ext:table-name "PREFIX_SET";
        sonic-ext:path-transformer "prefix_set_path_xfmr";
      }
    }

    deviation /oc-rpol:routing-policy/oc-rpol:defined-sets/oc-rpol:prefix-sets/oc-rpol:prefix-set/oc-rpol:name {
      deviate add {
            sonic-ext:field-transformer "prefix_set_name_fld_xfmr";
            sonic-ext:field-name "name";
      }
    }

    deviation /oc-rpol:routing-policy/oc-rpol:defined-sets/oc-rpol:prefix-sets/oc-rpol:prefix-set/oc-rpol:config/oc-rpol:name {
      deviate add {
            sonic-ext:field-transformer "prefix_set_name_fld_xfmr";
            sonic-ext:field-name "name";
      }
    }

    deviation /oc-rpol:routing-policy/oc-rpol:defined-sets/oc-rpol:prefix-sets/oc-rpol:prefix-set/oc-rpol:config/oc-rpol:mode {
        deviate add {
          sonic-ext:field-transformer "prefix_set_mode_fld_xfmr";
          sonic-ext:field-name "mode";
        }
    }

    deviation /oc-rpol:routing-policy/oc-rpol:defined-sets/oc-rpol:prefix-sets/oc-rpol:prefix-set/oc-rpol:state/oc-rpol:name {
      deviate add {
        sonic-ext:field-transformer "prefix_set_name_fld_xfmr";
        sonic-ext:field-name "name";
      }
    }

    deviation /oc-rpol:routing-policy/oc-rpol:defined-sets/oc-rpol:prefix-sets/oc-rpol:prefix-set/oc-rpol:state/oc-rpol:mode {
        deviate add {
          sonic-ext:field-transformer "prefix_set_mode_fld_xfmr";
          sonic-ext:field-name "mode";
        }
    }

    /* PREFIX table */

    deviation /oc-rpol:routing-policy/oc-rpol:defined-sets/oc-rpol:prefix-sets/oc-rpol:prefix-set/oc-rpol-ext:extended-prefixes  {
      deviate add {
        sonic-ext:table-name "NONE";
      }
    }

    deviation /oc-rpol:routing-policy/oc-rpol:defined-sets/oc-rpol:prefix-sets/oc-rpol:prefix-set/oc-rpol-ext:extended-prefixes/oc-rpol-ext:extended-prefix    {
      deviate add {
        sonic-ext:table-name "PREFIX";
        sonic-ext:key-transformer "prefix_key_xfmr";
      }
    }

    deviation /oc-rpol:routing-policy/oc-rpol:defined-sets/oc-rpol:prefix-sets/oc-rpol:prefix-set/oc-rpol-ext:extended-prefixes/oc-rpol-ext:extended-prefix/oc-rpol-ext:sequence-number {
      deviate add {
        sonic-ext:field-transformer "prefix_seq_no_fld_xfmr";
      }
    }

    deviation /oc-rpol:routing-policy/oc-rpol:defined-sets/oc-rpol:prefix-sets/oc-rpol:prefix-set/oc-rpol-ext:extended-prefixes/oc-rpol-ext:extended-prefix/oc-rpol-ext:ip-prefix {
      deviate add {
        sonic-ext:field-transformer "prefix_ip_prefix_fld_xfmr";
      }
    }

    deviation /oc-rpol:routing-policy/oc-rpol:defined-sets/oc-rpol:prefix-sets/oc-rpol:prefix-set/oc-rpol-ext:extended-prefixes/oc-rpol-ext:extended-prefix/oc-rpol-ext:masklength-range {
      deviate add {
        sonic-ext:field-transformer "prefix_masklength_range_fld_xfmr";
      }
    }

    deviation /oc-rpol:routing-policy/oc-rpol:defined-sets/oc-rpol:prefix-sets/oc-rpol:prefix-set/oc-rpol-ext:extended-prefixes/oc-rpol-ext:extended-prefix/oc-rpol-ext:config/oc-rpol-ext:sequence-number {
      deviate add {
        sonic-ext:field-transformer "prefix_seq_no_fld_xfmr";
        sonic-ext:field-name "sequence_number";
      }
    }

    deviation /oc-rpol:routing-policy/oc-rpol:defined-sets/oc-rpol:prefix-sets/oc-rpol:prefix-set/oc-rpol-ext:extended-prefixes/oc-rpol-ext:extended-prefix/oc-rpol-ext:config/oc-rpol-ext:ip-prefix {
      deviate add {
        sonic-ext:field-transformer "prefix_ip_prefix_fld_xfmr";
        sonic-ext:field-name "ip_prefix";
      }
    }

    deviation /oc-rpol:routing-policy/oc-rpol:defined-sets/oc-rpol:prefix-sets/oc-rpol:prefix-set/oc-rpol-ext:extended-prefixes/oc-rpol-ext:extended-prefix/oc-rpol-ext:config/oc-rpol-ext:masklength-range {
      deviate add {
        sonic-ext:field-transformer "prefix_masklength_range_fld_xfmr";
        sonic-ext:field-name "masklength_range";
      }
    }

    deviation /oc-rpol:routing-policy/oc-rpol:defined-sets/oc-rpol:prefix-sets/oc-rpol:prefix-set/oc-rpol-ext:extended-prefixes/oc-rpol-ext:extended-prefix/oc-rpol-ext:state/oc-rpol-ext:sequence-number {
      deviate add {
        sonic-ext:field-transformer "prefix_seq_no_fld_xfmr";
        sonic-ext:field-name "sequence_number";
      }
    }

    deviation /oc-rpol:routing-policy/oc-rpol:defined-sets/oc-rpol:prefix-sets/oc-rpol:prefix-set/oc-rpol-ext:extended-prefixes/oc-rpol-ext:extended-prefix/oc-rpol-ext:state/oc-rpol-ext:ip-prefix {
      deviate add {
        sonic-ext:field-transformer "prefix_ip_prefix_fld_xfmr";
        sonic-ext:field-name "ip_prefix";
      }
    }

    deviation /oc-rpol:routing-policy/oc-rpol:defined-sets/oc-rpol:prefix-sets/oc-rpol:prefix-set/oc-rpol-ext:extended-prefixes/oc-rpol-ext:extended-prefix/oc-rpol-ext:state/oc-rpol-ext:masklength-range {
      deviate add {
        sonic-ext:field-transformer "prefix_masklength_range_fld_xfmr";
        sonic-ext:field-name "masklength_range";
      }
    }

    deviation /oc-rpol:routing-policy/oc-rpol:defined-sets/oc-rpol:prefix-sets/oc-rpol:prefix-set/oc-rpol-ext:extended-prefixes/oc-rpol-ext:extended-prefix/oc-rpol-ext:config/oc-rpol-ext:action {
      deviate add {
        sonic-ext:field-transformer "prefix_action_fld_xfmr";
        sonic-ext:field-name "action";
      }
    }

    deviation /oc-rpol:routing-policy/oc-rpol:defined-sets/oc-rpol:prefix-sets/oc-rpol:prefix-set/oc-rpol-ext:extended-prefixes/oc-rpol-ext:extended-prefix/oc-rpol-ext:state/oc-rpol-ext:action {
      deviate add {
        sonic-ext:field-transformer "prefix_action_fld_xfmr";
        sonic-ext:field-name "action";
      }
    }

   /* COMMUNITY SETS */
   deviation /oc-rpol:routing-policy/oc-rpol:defined-sets/oc-bgp-pol:bgp-defined-sets/oc-bgp-pol:community-sets {
        deviate add {
            sonic-ext:table-name "NONE";
      }
    }

   deviation /oc-rpol:routing-policy/oc-rpol:defined-sets/oc-bgp-pol:bgp-defined-sets/oc-bgp-pol:community-sets/oc-bgp-pol:community-set {
        deviate add {
            sonic-ext:table-name "COMMUNITY_SET";
            sonic-ext:path-transformer "community_set_path_xfmr";
      }
    }

    deviation /oc-rpol:routing-policy/oc-rpol:defined-sets/oc-bgp-pol:bgp-defined-sets/oc-bgp-pol:community-sets/oc-bgp-pol:community-set/oc-bgp-pol:community-set-name {
      deviate add {
        sonic-ext:field-transformer "community_set_name_fld_xfmr";
      }
   }

    deviation /oc-rpol:routing-policy/oc-rpol:defined-sets/oc-bgp-pol:bgp-defined-sets/oc-bgp-pol:community-sets/oc-bgp-pol:community-set/oc-bgp-pol:config/oc-bgp-pol:community-set-name {
      deviate add {
        sonic-ext:field-transformer "community_set_name_fld_xfmr";
        sonic-ext:field-name "name";
      }
    }

    deviation /oc-rpol:routing-policy/oc-rpol:defined-sets/oc-bgp-pol:bgp-defined-sets/oc-bgp-pol:community-sets/oc-bgp-pol:community-set/oc-bgp-pol:config/oc-bgp-pol:match-set-options {
      deviate add {
        sonic-ext:field-transformer "community_match_set_options_fld_xfmr";
        sonic-ext:field-name "match_action";
      }
    }

    deviation /oc-rpol:routing-policy/oc-rpol:defined-sets/oc-bgp-pol:bgp-defined-sets/oc-bgp-pol:community-sets/oc-bgp-pol:community-set/oc-bgp-pol:config/oc-bgp-pol:community-member {
        deviate add {
            sonic-ext:field-transformer "community_member_fld_xfmr";
            sonic-ext:field-name "community_member";
        }
    }

    deviation /oc-rpol:routing-policy/oc-rpol:defined-sets/oc-bgp-pol:bgp-defined-sets/oc-bgp-pol:community-sets/oc-bgp-pol:community-set/oc-bgp-pol:state/oc-bgp-pol:match-set-options {
      deviate add {
        sonic-ext:field-transformer "community_match_set_options_fld_xfmr";
        sonic-ext:field-name "match_action";
      }
    }

    deviation /oc-rpol:routing-policy/oc-rpol:defined-sets/oc-bgp-pol:bgp-defined-sets/oc-bgp-pol:community-sets/oc-bgp-pol:community-set/oc-bgp-pol:state/oc-bgp-pol:community-member {
        deviate add {
            sonic-ext:field-transformer "community_member_fld_xfmr";
            sonic-ext:field-name "community_member";
        }
    }

    deviation /oc-rpol:routing-policy/oc-rpol:defined-sets/oc-bgp-pol:bgp-defined-sets/oc-bgp-pol:community-sets/oc-bgp-pol:community-set/oc-bgp-pol:state/oc-bgp-pol:community-set-name {
      deviate add {
        sonic-ext:field-transformer "community_set_name_fld_xfmr";
        sonic-ext:field-name "name";
      }
    }

    deviation /oc-rpol:routing-policy/oc-rpol:defined-sets/oc-bgp-pol:bgp-defined-sets/oc-bgp-pol:community-sets/oc-bgp-pol:community-set/oc-bgp-pol:config/oc-bgp-pol-ext:action {
      deviate add {
        sonic-ext:field-transformer "community_action_fld_xfmr";
        sonic-ext:field-name "action";
      }
    }

    deviation /oc-rpol:routing-policy/oc-rpol:defined-sets/oc-bgp-pol:bgp-defined-sets/oc-bgp-pol:community-sets/oc-bgp-pol:community-set/oc-bgp-pol:state/oc-bgp-pol-ext:action {
      deviate add {
        sonic-ext:field-transformer "community_action_fld_xfmr";
        sonic-ext:field-name "action";
      }
    }

   /* EXTENDED COMMUNITY */
    deviation /oc-rpol:routing-policy/oc-rpol:defined-sets/oc-bgp-pol:bgp-defined-sets/oc-bgp-pol:ext-community-sets {
        deviate add {
            sonic-ext:table-name "NONE";
        }
    }

    deviation /oc-rpol:routing-policy/oc-rpol:defined-sets/oc-bgp-pol:bgp-defined-sets/oc-bgp-pol:ext-community-sets/oc-bgp-pol:ext-community-set {
        deviate add {
            sonic-ext:table-name "EXTENDED_COMMUNITY_SET";
            sonic-ext:path-transformer "ext_community_set_path_xfmr";
        }
    }

    deviation /oc-rpol:routing-policy/oc-rpol:defined-sets/oc-bgp-pol:bgp-defined-sets/oc-bgp-pol:ext-community-sets/oc-bgp-pol:ext-community-set/oc-bgp-pol:ext-community-set-name {
      deviate add {
        sonic-ext:field-transformer "ext_community_set_name_fld_xfmr";
      }
    }

    deviation /oc-rpol:routing-policy/oc-rpol:defined-sets/oc-bgp-pol:bgp-defined-sets/oc-bgp-pol:ext-community-sets/oc-bgp-pol:ext-community-set/oc-bgp-pol:config/oc-bgp-pol:ext-community-set-name {
      deviate add {
        sonic-ext:field-transformer "ext_community_set_name_fld_xfmr";
        sonic-ext:field-name "name";
      }
    }

    deviation /oc-rpol:routing-policy/oc-rpol:defined-sets/oc-bgp-pol:bgp-defined-sets/oc-bgp-pol:ext-community-sets/oc-bgp-pol:ext-community-set/oc-bgp-pol:config/oc-bgp-pol:match-set-options {
      deviate add {
        sonic-ext:field-transformer "ext_community_match_set_options_fld_xfmr";
        sonic-ext:field-name "match_action";
      }
    }

    deviation /oc-rpol:routing-policy/oc-rpol:defined-sets/oc-bgp-pol:bgp-defined-sets/oc-bgp-pol:ext-community-sets/oc-bgp-pol:ext-community-set/oc-bgp-pol:config/oc-bgp-pol:ext-community-member {
        deviate add {
            sonic-ext:field-transformer "ext_community_member_fld_xfmr";
            sonic-ext:field-name "community_member";
        }
    }

    deviation /oc-rpol:routing-policy/oc-rpol:defined-sets/oc-bgp-pol:bgp-defined-sets/oc-bgp-pol:ext-community-sets/oc-bgp-pol:ext-community-set/oc-bgp-pol:config/oc-bgp-pol-ext:action {
      deviate add {
        sonic-ext:field-transformer "ext_community_action_fld_xfmr";
        sonic-ext:field-name "action";
      }
    }

    deviation /oc-rpol:routing-policy/oc-rpol:defined-sets/oc-bgp-pol:bgp-defined-sets/oc-bgp-pol:ext-community-sets/oc-bgp-pol:ext-community-set/oc-bgp-pol:state/oc-bgp-pol:match-set-options {
      deviate add {
        sonic-ext:field-transformer "ext_community_match_set_options_fld_xfmr";
        sonic-ext:field-name "match_action";
      }
    }

    deviation /oc-rpol:routing-policy/oc-rpol:defined-sets/oc-bgp-pol:bgp-defined-sets/oc-bgp-pol:ext-community-sets/oc-bgp-pol:ext-community-set/oc-bgp-pol:state/oc-bgp-pol:ext-community-member {
        deviate add {
            sonic-ext:field-transformer "ext_community_member_fld_xfmr";
            sonic-ext:field-name "community_member";
        }
    }

    deviation /oc-rpol:routing-policy/oc-rpol:defined-sets/oc-bgp-pol:bgp-defined-sets/oc-bgp-pol:ext-community-sets/oc-bgp-pol:ext-community-set/oc-bgp-pol:state/oc-bgp-pol:ext-community-set-name {
      deviate add {
        sonic-ext:field-transformer "ext_community_set_name_fld_xfmr";
        sonic-ext:field-name "name";
      }
    }

    deviation /oc-rpol:routing-policy/oc-rpol:defined-sets/oc-bgp-pol:bgp-defined-sets/oc-bgp-pol:ext-community-sets/oc-bgp-pol:ext-community-set/oc-bgp-pol:state/oc-bgp-pol-ext:action {
      deviate add {
        sonic-ext:field-transformer "ext_community_action_fld_xfmr";
        sonic-ext:field-name "action";
      }
    }

   /* AS PATH SETS */
    deviation /oc-rpol:routing-policy/oc-rpol:defined-sets/oc-bgp-pol:bgp-defined-sets/oc-bgp-pol:as-path-sets {
        deviate add {
            sonic-ext:table-name "NONE";
        }
    }

    deviation /oc-rpol:routing-policy/oc-rpol:defined-sets/oc-bgp-pol:bgp-defined-sets/oc-bgp-pol:as-path-sets/oc-bgp-pol:as-path-set {
        deviate add {
            sonic-ext:table-name "AS_PATH_SET";
            sonic-ext:path-transformer "as_path_set_path_xfmr";
        }
    }

    deviation /oc-rpol:routing-policy/oc-rpol:defined-sets/oc-bgp-pol:bgp-defined-sets/oc-bgp-pol:as-path-sets/oc-bgp-pol:as-path-set/oc-bgp-pol:as-path-set-name {
      deviate add {
        sonic-ext:field-transformer "as_path_set_name_fld_xfmr";
      }
    }

    deviation /oc-rpol:routing-policy/oc-rpol:defined-sets/oc-bgp-pol:bgp-defined-sets/oc-bgp-pol:as-path-sets/oc-bgp-pol:as-path-set/oc-bgp-pol:config/oc-bgp-pol:as-path-set-name {
      deviate add {
        sonic-ext:field-transformer "as_path_set_name_fld_xfmr";
        sonic-ext:field-name "name";
      }
    }

    deviation /oc-rpol:routing-policy/oc-rpol:defined-sets/oc-bgp-pol:bgp-defined-sets/oc-bgp-pol:as-path-sets/oc-bgp-pol:as-path-set/oc-bgp-pol:config/oc-bgp-pol:as-path-set-member {
        deviate add {
            sonic-ext:field-name "as_path_set_member";
        }
    }

    deviation /oc-rpol:routing-policy/oc-rpol:defined-sets/oc-bgp-pol:bgp-defined-sets/oc-bgp-pol:as-path-sets/oc-bgp-pol:as-path-set/oc-bgp-pol:state/oc-bgp-pol:as-path-set-name {
      deviate add {
        sonic-ext:field-transformer "as_path_set_name_fld_xfmr";
        sonic-ext:field-name "name";
      }
    }

    deviation /oc-rpol:routing-policy/oc-rpol:defined-sets/oc-bgp-pol:bgp-defined-sets/oc-bgp-pol:as-path-sets/oc-bgp-pol:as-path-set/oc-bgp-pol:state/oc-bgp-pol:as-path-set-member {
        deviate add {
            sonic-ext:field-name "as_path_set_member";
        }
    }

    deviation /oc-rpol:routing-policy/oc-rpol:defined-sets/oc-bgp-pol:bgp-defined-sets/oc-bgp-pol:as-path-sets/oc-bgp-pol:as-path-set/oc-bgp-pol:config/oc-bgp-pol-ext:action {
      deviate add {
        sonic-ext:field-transformer "as_path_set_action_fld_xfmr";
        sonic-ext:field-name "action";
      }
    }

    deviation /oc-rpol:routing-policy/oc-rpol:defined-sets/oc-bgp-pol:bgp-defined-sets/oc-bgp-pol:as-path-sets/oc-bgp-pol:as-path-set/oc-bgp-pol:state/oc-bgp-pol-ext:action {
      deviate add {
        sonic-ext:field-transformer "as_path_set_action_fld_xfmr";
        sonic-ext:field-name "action";
      }
    }

    /* AS PATH table */

    deviation /oc-rpol:routing-policy/oc-rpol:defined-sets/oc-bgp-pol:bgp-defined-sets/oc-bgp-pol:as-path-sets/oc-bgp-pol:as-path-set/oc-bgp-pol-ext:extended-as-path-sets {
        deviate add {
            sonic-ext:table-name "NONE";
        }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set {
        deviate add {
            sonic-ext:table-name "AS_PATH";
            sonic-ext:key-transformer "as_path_key_xfmr";
        }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:config/oc-bgp-pol-ext:as-path-set-member {
        deviate add {
            sonic-ext:field-name "as_path_member";
        }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:state/oc-bgp-pol-ext:as-path-set-member {
        deviate add {
            sonic-ext:field-name "as_path_member";
        }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:config/oc-bgp-pol-ext:action {
      deviate add {
        sonic-ext:field-transformer "as_path_action_fld_xfmr";
        sonic-ext:field-name "action";
      }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:state/oc-bgp-pol-ext:action {
      deviate add {
        sonic-ext:field-transformer "as_path_action_fld_xfmr";
        sonic-ext:field-name "action";
      }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:sequence-number {
      deviate add {
        sonic-ext:field-transformer "as_path_seq_no_fld_xfmr";
        sonic-ext:field-name "sequence_number";
      }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:config/oc-bgp-pol-ext:sequence-number {
      deviate add {
        sonic-ext:field-transformer "as_path_seq_no_fld_xfmr";
        sonic-ext:field-name "sequence_number";
      }
    }

    deviation /oc-rpol:routing-policy/oc-rpol:defined-sets/oc-bgp-pol:bgp-defined-sets/oc-bgp-pol:as-path-sets/oc-bgp-pol:as-path-set/oc-bgp-pol-ext:extended-as-path-sets/oc-bgp-pol-ext:extended-as-path-set/oc-bgp-pol-ext:state/oc-bgp-pol-ext:sequence-number {
      deviate add {
        sonic-ext:field-transformer "as_path_seq_no_fld_xfmr";
        sonic-ext:field-name "sequence_number";
      }
    }

    deviation /oc-rpol:routing-policy/oc-rpol-ext:ip/oc-rpol-ext:ipv4 {
      deviate add {
          sonic-ext:db-name "CONFIG_DB";
          sonic-ext:table-name "IPV4_PROTOCOL_RMAP";
          sonic-ext:user-role-priv "write:netadmin";
      }
    }

    deviation /oc-rpol:routing-policy/oc-rpol-ext:ip/oc-rpol-ext:ipv6 {
      deviate add {
          sonic-ext:db-name "CONFIG_DB";
          sonic-ext:table-name "IPV6_PROTOCOL_RMAP";
          sonic-ext:user-role-priv "write:netadmin";
      }
    }
}
