module openconfig-platform-deviation {

    yang-version "1";

    // namespace
    namespace "http://openconfig.net/yang/platform/deviation/extension";

    prefix "oc-platform-dev";

    // import some basic types
    import openconfig-platform { prefix oc-platform; }
    import openconfig-extensions { prefix oc-ext; }

    organization
      "SONiC";

    contact
      "SONiC";

    description
      "This module describes a YANG model for openconfig-platform deviations.";

    oc-ext:openconfig-version "0.1.0";

    revision "2023-10-18" {
      description
        "Add PCIe deviations.";
      reference "0.1.0";
    }

    deviation /oc-platform:components/oc-platform:component/oc-platform:state/oc-platform:pcie {
      deviate not-supported;
    }
}
