module sonic-buffer-profile {
	namespace "http://github.com/Azure/sonic-buffer-profile";
	prefix bpf;

	import sonic-common {
		prefix cmn;
	}

	import sonic-buffer-pool {
		prefix bpl;
	}

	import sonic-extension {
		prefix sonic-ext;
	}

	organization
		"SONiC";

	contact
		"SONiC";

	description
		"SONIC BUFFER PROFILE";

	revision 2019-05-15 {
		description
			"Initial revision.";
	}

	typedef qos_buffer_type {
		type enumeration {
			enum ingress;
			enum egress;
		}
	}

	container sonic-buffer-profile {

		container BUFFER_PROFILE {

			list BUFFER_PROFILE_LIST {
				key "name";
                                sonic-ext:custom-validation ValidateBufferConfCapability;
                                sonic-ext:custom-validation ValidateBufferConfigsInitilized;
                                sonic-ext:custom-validation ValidateProfileCfgForBuffTblRef;
                                sonic-ext:custom-validation ValidateBufferLimits;
                                leaf name {
					type string;
					must "(not(starts-with(current(), 'pg_lossless')))" {
						error-app-tag reserved-profile-name;
						error-message "User defined profile starts with pg_lossless is not allowed, Try different profile name!";
                                        }
				}

				leaf type {
					type qos_buffer_type;
					must "(/cmn:operation/cmn:operation = 'DELETE') or " +
							"not(current()/../pool) or " +
							"(/bpl:sonic-buffer-pool/bpl:BUFFER_POOL/bpl:BUFFER_POOL_LIST[bpl:name=current()/../pool]/bpl:type = current())" {
						error-app-tag profile-type-not-match-buffer-pool;
						error-message "Profile type does not match referenced buffer-pool";
					}
				}

                                leaf static_th {
                                    type uint64;
                                    must "not(current()/../dynamic_th)" {
                                        error-message "Configuring Static and dynamic threshold in the same profile is not allowed.";
                                    }
                                }

                                leaf dynamic_th {
                                    type int64;
                                    must "not(current()/../static_th)" {
                                        error-message "Configuring Static and dynamic threshold in the same profile is not allowed.";
                                    }
                                }

                                leaf size {
                                    mandatory true;
                                    type uint64 {
                                        range "0..18796" {
                                            error-message "Invalid reserved value";
                                        }
                                    }
                                }

                                leaf pool {
                                    mandatory true;
                                    type leafref {
                                        path "/bpl:sonic-buffer-pool/bpl:BUFFER_POOL/bpl:BUFFER_POOL_LIST/bpl:name";
                                    }
                                    must "(/cmn:operation/cmn:operation = 'DELETE') or " +
                                        "not(/bpl:sonic-buffer-pool/bpl:BUFFER_POOL/bpl:BUFFER_POOL_LIST[bpl:name=current()]/bpl:type and " +
                                        "current()/../type and " +
                                        "(/bpl:sonic-buffer-pool/bpl:BUFFER_POOL/bpl:BUFFER_POOL_LIST[bpl:name=current()/../pool]/bpl:type != current()/../type))" {
                                            error-app-tag profile-type-not-match-buffer-pool;
                                            error-message "Profile type does not match referenced buffer-pool";
                                        }
                                }

                                leaf xon_offset {
                                    type uint64 {
                                        range "1..18432" {
                                            error-message "Invalid XON offset value";
                                        }
                                    }
                                }

                                leaf xon {
                                    type uint64 {
                                        range "1..18432" {
                                            error-message "Invalid XON value";
                                        }
                                    }
                                }

                                leaf xoff {
                                    type uint64;
                                    must "(current()/../pool = 'ingress_lossless_pool')" {
                                        error-app-tag buffer-profile-xoff-egress-not-allowed;
                                        error-message "Buffer profile xoff with type egress not allowed";
                                    }
                                }
                        }
		}
	}
}
