submodule openconfig-bgp-global {

  belongs-to openconfig-bgp {
    prefix "oc-bgp";
  }

  import openconfig-extensions { prefix oc-ext; }
  import openconfig-yang-types { prefix oc-yang; }
  import openconfig-inet-types { prefix oc-inet; }
  import openconfig-bgp-types  { prefix oc-bgp-types; }
  import openconfig-routing-policy { prefix oc-rpol; }

  // Include common submodules
  include openconfig-bgp-common;
  include openconfig-bgp-common-multiprotocol;
  include openconfig-bgp-peer-group;
  include openconfig-bgp-common-structure;

  // meta
  organization
    "OpenConfig working group";

  contact
    "OpenConfig working group
    netopenconfig@googlegroups.com";

  description
    "This sub-module contains groupings that are specific to the
    global context of the OpenConfig BGP module";

  oc-ext:openconfig-version "7.0.2";

  revision "2024-02-05" {
    description
      "Add ASN Notation for asdot/asdot+ support.";
    reference "7.0.2";
  }

  revision "2023-02-09" {
    description
      "Updated write-quanta value range.";
    reference "7.0.1";
  }

  revision "2021-05-27" {
    description
      "Enhance BGP modules for additional features.";
    reference "7.0.0";
  }

  revision "2019-07-10" {
    description
      "Normalise timestamp units to nanoseconds.";
    reference "6.0.0";
  }

  revision "2019-05-28" {
    description
      "Clarify prefix counter descriptions, add received-pre-policy
      counter.";
    reference "5.2.0";
  }

  revision "2019-04-16" {
    description
      "Add BGP RIB to the top-level BGP container";
    reference "5.1.0";
  }

  revision "2018-11-21" {
    description
      "Add OpenConfig module metadata extensions.";
    reference "5.0.2";
  }

  revision "2018-08-20" {
    description
      "Correct description of AFI-SAFI enabled leaf.";
    reference "5.0.1";
  }

  revision "2018-04-11" {
    description
      "Correct naming of BGP maximum prefix warning percentage leaf.";
    reference "5.0.0";
  }

  revision "2018-03-20" {
    description
      "Added SR-TE policy SAFI";
    reference "4.1.0";
  }

  revision "2017-07-10" {
    description
      "Add error notifications; moved add-paths config; add AS
      prepend policy features; removed unneeded config leaves";
    reference "4.0.0";
  }

  revision "2017-02-02" {
    description
      "Bugfix to remove remaining global-level policy data";
    reference "3.0.1";
  }

  revision "2017-01-26" {
    description
      "Add dynamic neighbor support, migrate to OpenConfig types";
    reference "3.0.0";
  }

  revision "2016-06-21" {
    description
      "OpenConfig BGP refactor";
    reference "2.1.1";
  }

  typedef as-notation-type {
    type enumeration {
      enum ASPLAIN {
        description
          "AS numbers are represented using decimal integer notation.";
      }
      enum ASDOT {
        description
          "AS numbers that are less than 65536 are represented using the asplain notation, while
           AS number that are equal to or greater than 65536 are represented using asdot+ notation.";
      }
      enum ASDOT_PLUS {
        description
          "AS numbers are represented using a notation of two integer values joined by a period character:
           <high order 16-bit value in decimal>.<low order 16-bit value in decimal>.";
      }
    }
    description
      "A textual representation for Autonomous System (AS) numbers as defined in RFC 5396.";
  }

  grouping bgp-global-config {
    description
      "Global configuration options for the BGP router.";

    leaf as {
      type oc-inet:as-number;
      mandatory true;
      description
        "Local autonomous system number of the router.  Uses
        the 32-bit as-number type from the model in RFC 6991.";
    }

    leaf router-id {
      type oc-yang:dotted-quad;
      description
        "Router id of the router - an unsigned 32-bit integer
        expressed in dotted quad notation.";
      reference
        "RFC4271 - A Border Gateway Protocol 4 (BGP-4),
        Section 4.2";
    }

    leaf disable-ebgp-connected-route-check {
      type boolean;
      description
        "Disable EBGP conntected route check, this helps to connect EBGP neighbors multi-hops away.";
    }

    leaf fast-external-failover {
      type boolean;
      default true;
      description
        "This causes bgp to take down ebgp peers immediately when a link flaps.";
    }

    leaf network-import-check {
      type boolean;
      default true;
      description
        "This helps to advertise a BGP route not present in the routing table.";
    }

    leaf graceful-shutdown {
      type boolean;
      description
        "This helps to reduce the amount of lost traffic when taking BGP sessions down for maintenance.";
    }

    leaf clnt-to-clnt-reflection {
      type boolean;
      description
        "Enable client to client route reflection.";
    }

    leaf max-dynamic-neighbors {
      type uint16 {
        range 1..5000;
      }
      description
        "Maximum number of BGP dynamic neighbors that can be created.";
    }

    leaf read-quanta {
      type uint8 {
        range 1..10;
      }
      description
        "This indicates how many packets to read from peer socket per I/O cycle";
    }

    leaf write-quanta {
      type uint8 {
        range 1..64;
      }
      description
        "This indicates how many packets to write to peer socket per run";
    }

    leaf coalesce-time {
      type uint32;
      description
        "Subgroup coalesce timer value in milli-sec";
    }

    leaf route-map-process-delay {
      type uint16 {
        range 0..600;
      }
      description
        "0 disables the timer, no route updates happen when route-maps change";
    }

    leaf deterministic-med {
      type boolean;
      description
        "Pick the best-MED path among paths advertised from the neighboring AS.";
    }

    leaf hold-time {
      type decimal64 {
        fraction-digits 2;
      }
      default 180;
      description
        "Time interval in seconds that a BGP session will be
        considered active in the absence of keepalive or other
        messages from the peer.  The hold-time is typically
        set to 3x the keepalive-interval.";
    }

    leaf keepalive-interval {
      type decimal64 {
        fraction-digits 2;
      }
      default 60;
      description
        "Time interval in seconds between transmission of keepalive
        messages to the neighbor.  Typically set to 1/3 the
        hold-time.";
    }

    leaf ebgp-requires-policy {
      type boolean;
      default false;
      description
        "This causes bgp to make in and out policy mandatory for eBGP peers (RFC8212).";
    }

    leaf as-notation {
        type as-notation-type;
        description
           "AS-notation for BGP AS numbers (default is ASPLAIN when unspecified.)";
    }
  }

  grouping bgp-global-state {
    description
      "Operational state parameters for the BGP neighbor";

    uses bgp-common-state;
  }

  grouping bgp-global-default-route-distance-config {
    description
      "Configuration options relating to the administrative distance
      (or preference) assigned to routes received from different
      sources (external, internal, and local).";

    leaf external-route-distance {
      type uint8 {
        range "1..255";
      }
      description
        "Administrative distance for routes learned from external
        BGP (eBGP).";
    }
    leaf internal-route-distance {
      type uint8 {
        range "1..255";
      }
      description
        "Administrative distance for routes learned from internal
        BGP (iBGP).";
    }

    leaf local-route-distance {
      type uint8 {
        range "1..255";
      }
      description
        "Administrative distance for local routes.";
    }
  }

  grouping bgp-global-confederation-config {
    description
      "Configuration options specifying parameters when the local
      router is within an autonomous system which is part of a BGP
      confederation.";

    leaf identifier {
      type oc-inet:as-number;
      description
        "Confederation identifier for the autonomous system.
        Setting the identifier indicates that the local-AS is part
        of a BGP confederation.";
    }

    leaf-list member-as {
      type oc-inet:as-number;
      description
        "Remote autonomous systems that are to be treated
        as part of the local confederation.";
    }
  }

  grouping bgp-global-dynamic-neighbors {
    description
      "Grouping containing configuration relating to dynamic peers.";

    container dynamic-neighbor-prefixes {
      description
        "A list of IP prefixes from which the system should:
          - Accept connections to the BGP daemon
          - Dynamically configure a BGP neighbor corresponding to the
            source address of the remote system, using the parameters
            of the specified peer-group.
         For such neighbors, an entry within the neighbor list should
         be created, indicating that the peer was dynamically
         configured, and referencing the peer-group from which the
         configuration was derived.";

      list dynamic-neighbor-prefix {
        key "prefix";
        description
          "An individual prefix from which dynamic neighbor
          connections are allowed.";

        leaf prefix {
          type leafref {
            path "../config/prefix";
          }
          description
            "Reference to the IP prefix from which source connections
            are allowed for the dynamic neighbor group.";
        }

        container config {
          description
            "Configuration parameters relating to the source prefix
            for the dynamic BGP neighbor connections.";

          uses bgp-global-dynamic-neighbor-config;
        }

        container state {
          config false;
          description
            "Operational state parameters relating to the source
            prefix for the dynamic BGP neighbor connections.";

          uses bgp-global-dynamic-neighbor-config;
        }
      }
    }
  }

  grouping bgp-global-dynamic-neighbor-config {
    description
      "Configuration parameters relating to an individual prefix from
      which dynamic neighbors are accepted.";

    leaf prefix {
      type oc-inet:ip-prefix;
      description
        "The IP prefix within which the source address of the remote
        BGP speaker must fall to be considered eligible to the
        dynamically configured."; }

    leaf peer-group {
      type leafref {
        // At bgp/global/dynamic-neighbor-prefixes/dynamic-neighbor
        // prefix/config/peer-group
        path "../../../../../peer-groups/peer-group/config/" +
             "peer-group-name";
      }
      description
        "The peer-group within which the dynamic neighbor will be
        configured.  The configuration parameters used for the dynamic
        neighbor are those specified within the referenced peer
        group.";
    }
  }

  grouping bgp-global-route-reflector-config {
    description
      "Configuration data for router reflector global address family";

    leaf route-reflector-cluster-id {
      type oc-bgp-types:rr-cluster-id-type;
      description
        "route-reflector cluster id to use when local router is
        configured as a route reflector.";
    }

    leaf allow-outbound-policy {
      type boolean;
      description
        "This leaf indicates whether to allow the outbound policy.";
    }
  }

  grouping bgp-global-route-reflector-top {
    description
      "Configuration parameters determining whether the behaviour of
      the local system when acting as a route-reflector";

    container route-reflector {
      description
        "Parameters relating to BGP route reflector";

      container config {
        description
          "Configuration options for BGP route reflector";
        uses bgp-global-route-reflector-config;
      }

      container state {
        config false;
        description
          "State information for BGP route reflector";
        uses bgp-global-route-reflector-config;
      }
    }
  }

  grouping bgp-global-defaults-config {
    description
      "Configuration data for global defaults";

    leaf ipv4-unicast {
      type boolean;
      description
        "Activate ipv4-unicast for a peer by default";
    }

    leaf local-preference {
      type uint32;
      description
        "Configure default local preference value.";
    }

    leaf show-hostname {
      type boolean;
      description
        "Show hostname in BGP dumps.";
    }

    leaf shutdown {
      type boolean;
      description
        "Apply administrative shutdown to newly configured peers.";
    }

    leaf subgroup-pkt-queue-max {
      type uint8 {
        range 20..100;
      }
      description
        "Configure subgroup packet queue max.";
    }
  }

  grouping bgp-global-defaults-top {
    description
      "Configuration data for global defaults";

    container global-defaults {
      description
        "Parameters relating to BGP defaults";
      container config {
        description
          "Configuration options for BGP global defaults";
        uses bgp-global-defaults-config;
      }
      container state {
        config false;
        description
          "State information for BGP global defaults";
        uses bgp-global-defaults-config;
      }
    }
  }

  grouping bgp-global-update-delay-config {
    description
      "Configuration data for update delay under global level";

    leaf max-delay {
      type uint16 {
        range 0..3600;
      }
      description
        "Maximum delay for best path calculation.";
    }

    leaf establish-wait {
      type uint16 {
        range 0..3600;
      }
      description
        "Maximum delay for updates.";
    }
  }

  grouping bgp-global-update-delay-top {
    description
      "Configuration data for update delay under global level";

    container update-delay {
      description
        "Parameters relating to force initial delay for best-path and updates.";

      container config {
        description
          "Configuration options for BGP update delay";
        uses bgp-global-update-delay-config;
      }

      container state {
        config false;
        description
          "State information for BGP update delay";
        uses bgp-global-update-delay-config;
      }
    }
  }

  grouping bgp-global-max-med-config {
    description
      "Configuration data for max med under global level";

    leaf time {
      type uint32{
        range 5..86400;
      }
      description
        "Time (seconds) period for max-med";
    }

    leaf max-med-val {
      type uint32;
      description
        "Max MED value to be used";
    }

    leaf administrative {
      type boolean;
      description
        "Administratively applied, for an indefinite period.";
    }

    leaf admin-max-med-val {
      type uint32;
      description
        "Administrative Max MED value to be used";
    }
  }

  grouping bgp-global-max-med-top {
    description
      "Configuration data for max med under global level";

    container max-med {
      description
        "Parameters relating to advertise routes with max-med.";

      container config {
        description
          "Configuration options for BGP max med.";
        uses bgp-global-max-med-config;
      }

      container state {
        config false;
        description
          "State information for BGP max med.";
        uses bgp-global-max-med-config;
      }
    }
  }

  grouping bgp-global-mp-afi-safi-aggregate-address-config {
    description
      "Configuration data for aggregate address under global address family";

    leaf prefix {
      type oc-inet:ip-prefix;
      description
        "This specifies an aggregate address.";
    }

    leaf policy-name {
      type leafref {
        path "/oc-rpol:routing-policy/oc-rpol:policy-definitions/" +
          "oc-rpol:policy-definition/oc-rpol:name";
      }
      description
        "A reference to a routing policy which can be used to
        restrict the prefixes for which advertisement is enabled";
    }

    leaf as-set {
      type boolean;
      description
        "This leaf indicates whether the resulting routes include AS set.";
    }

    leaf summary-only {
      type boolean;
      description
        "This leaf indicates resulting routes will not be announced.";
    }
  }

  grouping bgp-global-mp-afi-safi-aggregate-address-top {
    description
      "Configuration data for route aggregation.";
    container aggregate-address-config {
      description
        "Parameters relating to BGP route aggregation.";

      list aggregate-address {
        key "prefix";
        description
          "BGP aggregate address configurtion.";

        leaf prefix {
          type leafref {
            path "../config/prefix";
          }
          description
            "Reference to the aggregate prefix.";
        }

        container config {
          description
            "Configuration options for BGP route aggregation";
          uses bgp-global-mp-afi-safi-aggregate-address-config;
        }
        container state {
          config false;
          description
            "State information for BGP route aggregation";
          uses bgp-global-mp-afi-safi-aggregate-address-config;
        }
      }
    }
  }

  grouping bgp-global-mp-afi-safi-network-config {
    description
      "Configuration data for network address under global address family";

    leaf prefix {
      type oc-inet:ip-prefix;
      description
        "This specifies a network address.";
    }

    leaf policy-name {
      type leafref {
        path "/oc-rpol:routing-policy/oc-rpol:policy-definitions/" +
          "oc-rpol:policy-definition/oc-rpol:name";
      }
      description
        "A reference to a routing policy which can be used to
        restrict the prefixes for which advertisement is enabled";
    }

    leaf backdoor {
      type boolean;
      description
        "This leaf indicates whether to make the prefix less perferred over IGP route
        and the prefix will not be advertised to the BGP peers.";
    }
  }

  grouping bgp-global-mp-afi-safi-network-top {
    description
      "Configuration data for BGP network announcement.";

    container network-config {
      description
        "Parameters relating to BGP network announcement.";

      list network {
        key "prefix";
        description
          "BGP network configurtion.";

        leaf prefix {
          type leafref {
            path "../config/prefix";
          }
          description
            "Reference to the IP network.";
        }

        container config {
          description
            "Configuration options for BGP network.";
          uses bgp-global-mp-afi-safi-network-config;
        }
        container state {
          config false;
          description
            "State information for BGP network.";
          uses bgp-global-mp-afi-safi-network-config;
        }
      }
    }
  }

  grouping bgp-global-mp-afi-safi-default-route-distance-top {
    description
      "Configuration data related to default route distance.";

    container default-route-distance {
      description
        "Administrative distance (or preference) assigned to
        routes received from different sources
        (external, internal, and local).";

      container config {
        description
          "Configuration parameters relating to the default route
          distance";
        uses bgp-global-default-route-distance-config;
      }
      container state {
        config false;
        description
          "State information relating to the default route distance";
        uses bgp-global-default-route-distance-config;
      }
    }
  }

  grouping bgp-global-mp-afi-safi-backup-paths-config {
    description
      "Configuration data for backup-path selection under address-family";
    leaf compute {
      type boolean;
      description
        "This leaf indicates whether backup-path compute is enabled for
        this AFI-SAFI";
    }

    leaf install {
      type boolean;
      description
        "Install the backup path";
    }
  }

  grouping bgp-global-mp-afi-safi-backup-paths-top {
    description
      "Configuration data for backup-path selection";
    container backup-paths {
      description
        "Parameters relating to BGP backup-paths";
      container config {
        description
          "Configuration options for BGP backup-paths";
        uses bgp-global-mp-afi-safi-backup-paths-config;
      }
      container state {
        config false;
        description
          "State information for BGP backup-paths";
        uses bgp-global-mp-afi-safi-backup-paths-config;
      }
    }
  }

  grouping bgp-global-mp-afi-safi-route-flap-damping-config {
    description
      "Configuration data for route flap damping under global level";
    leaf enabled {
      type boolean;
      default false;
      description
        "This leaf indicates whether route flap damping is enabled for
        this AFI-SAFI";
    }

    leaf half-life {
      type uint8 {
        range 1..45;
      }
      description
        "Half-life time for the penalty.";
    }

    leaf reuse-threshold {
      type uint16 {
        range 1..20000;
      }
      description
        "Value to start reusing a route";
    }

    leaf suppress-threshold {
      type uint16 {
        range 1..20000;
      }
      description
        "Value to start suppressing a route";
    }

    leaf max-suppress {
      type uint8 {
        range 1..255;
      }
      description
        "Maximum duration to suppress a stable route.";
    }
  }

  grouping bgp-global-mp-afi-safi-route-flap-damping-top {
    description
      "Configuration data for global route flap damping";
    container route-flap-damping {
      description
        "Parameters relating to BGP route flap damping";
      container config {
        description
          "Configuration options for BGP route flap damping";
        uses bgp-global-mp-afi-safi-route-flap-damping-config;
      }
      container state {
        config false;
        description
          "State information for BGP route flap damping";
        uses bgp-global-mp-afi-safi-route-flap-damping-config;
      }
    }
  }

  grouping bgp-global-mp-afi-safi-route-policy-config {
    description
      "Configuration data for global routing policy";
    leaf table-map-name {
      type leafref {
        path "/oc-rpol:routing-policy/oc-rpol:policy-definitions/" +
          "oc-rpol:policy-definition/oc-rpol:name";
      }
      description
        "A reference to a routing policy which can be used to
        apply policy on route updates from BGP to RTM.";
    }
  }

  grouping bgp-global-mp-all-afi-safi-list-contents {
    description
      "A grouping used for contents of the list of AFI-SAFI
      entries at the global BGP level.";

    // import and export policy included for the afi/safi

    uses bgp-common-mp-ipv4-unicast-group;
    uses bgp-common-mp-ipv6-unicast-group;
    uses bgp-common-mp-ipv4-labeled-unicast-group;
    uses bgp-common-mp-ipv6-labeled-unicast-group;
    uses bgp-common-mp-l3vpn-ipv4-unicast-group;
    uses bgp-common-mp-l3vpn-ipv6-unicast-group;
    uses bgp-common-mp-l3vpn-ipv4-multicast-group;
    uses bgp-common-mp-l3vpn-ipv6-multicast-group;
    uses bgp-common-mp-l2vpn-vpls-group;
    uses bgp-common-mp-l2vpn-evpn-group;
    uses bgp-common-mp-srte-policy-ipv4-group;
    uses bgp-common-mp-srte-policy-ipv6-group;
  }

  grouping bgp-global-afi-safi-list {
    description
      "List of address-families associated with the BGP instance";

    list afi-safi {
      key "afi-safi-name";

      description
        "AFI,SAFI configuration available for the
        neighbour or group";

      leaf afi-safi-name {
        type leafref {
          path "../config/afi-safi-name";
        }
        description
          "Reference to the AFI-SAFI name used as a key
          for the AFI-SAFI list";
      }

      container config {
        description
          "Configuration parameters for the AFI-SAFI";
        uses bgp-common-mp-afi-safi-config;
        uses bgp-global-mp-afi-safi-route-policy-config;
      }
      container state {
        config false;
        description
          "State information relating to the AFI-SAFI";
        uses bgp-common-mp-afi-safi-config;
        uses bgp-global-mp-afi-safi-route-policy-config;
        uses bgp-common-state;
      }

      container graceful-restart {
        description
          "Parameters relating to BGP graceful-restart";
        container config {
          description
            "Configuration options for BGP graceful-restart";
          uses bgp-common-mp-afi-safi-graceful-restart-config;
        }
        container state {
          config false;
          description
            "State information for BGP graceful-restart";
          uses bgp-common-mp-afi-safi-graceful-restart-config;
        }
      }

      uses bgp-common-route-selection-options;
      uses bgp-common-global-group-use-multiple-paths;
      uses bgp-common-structure-neighbor-group-add-paths;
      uses bgp-global-mp-all-afi-safi-list-contents;
      uses bgp-global-mp-afi-safi-aggregate-address-top;
      uses bgp-global-mp-afi-safi-network-top;
      uses bgp-global-mp-afi-safi-default-route-distance-top;
      uses bgp-global-mp-afi-safi-route-flap-damping-top;
      uses bgp-global-mp-afi-safi-backup-paths-top;
    }
  }

  // Structural groupings
  grouping bgp-global-base {
    description
      "Global configuration parameters for the BGP router";

    container config {
      description
        "Configuration parameters relating to the global BGP router";
      uses bgp-global-config;
    }
    container state {
      config false;
      description
        "State information relating to the global BGP router";
      uses bgp-global-config;
      uses bgp-global-state;
    }

    container default-route-distance {
      description
        "Administrative distance (or preference) assigned to
        routes received from different sources
        (external, internal, and local).";

      container config {
        description
          "Configuration parameters relating to the default route
          distance";
        uses bgp-global-default-route-distance-config;
      }
      container state {
        config false;
        description
          "State information relating to the default route distance";
        uses bgp-global-default-route-distance-config;
      }
    }

    container confederation {
      description
        "Parameters indicating whether the local system acts as part
        of a BGP confederation";

      container config {
        description
          "Configuration parameters relating to BGP confederations";
        uses bgp-global-confederation-config;
      }
      container state {
        config false;
        description
          "State information relating to the BGP confederations";
        uses bgp-global-confederation-config;
      }
    }

    container graceful-restart {
      description
        "Parameters relating the graceful restart mechanism for BGP";
      container config {
        description
          "Configuration parameters relating to graceful-restart";
        uses bgp-common-graceful-restart-config;
      }
      container state {
        config false;
        description
          "State information associated with graceful-restart";
        uses bgp-common-graceful-restart-config;
      }
    }

    uses bgp-common-global-group-use-multiple-paths;
    uses bgp-common-route-selection-options;

    container afi-safis {
      description
        "Address family specific configuration";
      uses bgp-global-afi-safi-list;
    }

    uses bgp-global-dynamic-neighbors;
    uses bgp-common-structure-global-neighbor-group-logging-options;
    uses bgp-global-route-reflector-top;
    uses bgp-global-defaults-top;
    uses bgp-global-update-delay-top;
    uses bgp-global-max-med-top;
  }

}
