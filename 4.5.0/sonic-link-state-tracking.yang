module sonic-link-state-tracking {
    namespace "http://github.com/Azure/sonic-link-state-tracking";
    prefix slst;
    yang-version 1.1;

    import sonic-port {
        prefix sprt;
    }

    import sonic-portchannel {
        prefix spc;
    }

    import sonic-vlan {
        prefix svlan;
    }

    import sonic-extension {
        prefix sonic-ext; 
    }

    import sonic-interface {
        prefix sint;
    }

    organization
        "SONiC";

    contact
        "SONiC";

    description
        "SONIC Link state tracking";

    revision 2019-12-01 {
        description
            "Initial revision.";
    }

    container sonic-link-state-tracking {

        container INTF_TRACKING {

            list INTF_TRACKING_LIST { 
                key "name";
                max-elements 1;

                leaf name {
                    type string {
                        pattern '[a-zA-Z0-9]{1}([-a-zA-Z0-9@$+#_]{0,63})';
                        length 1..64;
                    }
                }

                leaf description {
                    type string {
                        length 1..255;
                    }
                }

                leaf timeout {
                     type uint16 {
                        range "1..1800" {
                            error-message "Timeout value is out of range (1-1800)";
                        }
                    }
                    default 60;
                }

                leaf-list upstream {
                    sonic-ext:custom-validation ValidateLinkStateTrackIntfCfg;
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/sint:sonic-interface/sint:VLAN_SUB_INTERFACE/sint:VLAN_SUB_INTERFACE_LIST/sint:id";
                        }
                    }
                }

                leaf-list downstream {
                    sonic-ext:custom-validation ValidateLinkStateTrackIntfCfg;
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                        type enumeration {
                            enum all-mclag;
                            enum all-evpn-es;
                        }
                    }
                }

                leaf threshold_type {
                    type enumeration {
                        enum ONLINE_PERCENTAGE;
                    }
                }

                leaf threshold_up {
                    type decimal64 {
                        fraction-digits 3;
                    }
                    must "(current()/../threshold_type != '')" {
                        error-message "Threshold type must be set prior to setting threshold value.";
                    }
                    must "(not(current()/../threshold_down)) or (current() >= current()/../threshold_down)" {
                        error-message "Threshold up must be greater than threshold down value.";
                    } 
                    must "((current()/../threshold_type = 'ONLINE_PERCENTAGE') and (current() >= 0) and (current() <= 100))" {
                        error-message "Threshold up value must be in range 0-100%";
                    }
                }

                leaf threshold_down {
                    type decimal64 {
                        fraction-digits 3;
                    }
                    must "(current()/../threshold_type != '')" {
                        error-message "Threshold type must be set prior to setting threshold value";
                    }
                    must "(not(current()/../threshold_up)) or (current() <= current()/../threshold_up)" {
                        error-message "Threshold down must be less than threshold up value.";
                    }
                    must "((current()/../threshold_type = 'ONLINE_PERCENTAGE') and (current() >= 0) and (current() <= 100))" {
                        error-message "Threshold down value must be in range 0-100%";
                    }
                }
            }
        }

        container INTF_TRACKING_TABLE {
            sonic-ext:db-name "STATE_DB"; 
            sonic-ext:key-delim "|"; 
            config false;
            list INTF_TRACKING_TABLE_LIST { 
                key "name";
                leaf name {
                    type string; 
                }
                leaf description {
                    type string;
                }
                leaf timeout {
                    type uint16;
                }
                leaf bringup_start_time {
                    type uint64;
                }
                leaf-list upstream {
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/sint:sonic-interface/sint:VLAN_SUB_INTERFACE/sint:VLAN_SUB_INTERFACE_LIST/sint:id";
                        }
                    }
                }
                leaf-list upstream_status {
                    type string;
                }
                leaf-list downstream {
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                    }
                }
                leaf-list downstream_status {
                    type string;
                }
                leaf threshold_type {
                    type string;
                }
                leaf threshold_up {
                    type decimal64 {
                        fraction-digits 3;
                    }
                }
                leaf threshold_down {
                    type decimal64 {
                        fraction-digits 3;
                    }
                }
            }
        }
    }
}
