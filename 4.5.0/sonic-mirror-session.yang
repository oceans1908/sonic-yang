module sonic-mirror-session {
    namespace "http://github.com/Azure/sonic-mirror-session";
    prefix sms;
    yang-version 1.1;

    import ietf-inet-types {
        prefix inet;
    }

    import sonic-extension {
        prefix sonic-ext;
    }

    import sonic-port {
        prefix prt;
    }

    import sonic-portchannel {
        prefix spc;
    }


    organization
        "SONiC";

    contact
        "SONiC";

    description
        "SONIC MIRROR SESSION";

    revision 2019-05-15 {
        description
            "Initial revision.";
    }

    container sonic-mirror-session {

        container MIRROR_SESSION {

            list MIRROR_SESSION_LIST {
                key "name";

                leaf name {
                    type string {
                        pattern '[a-zA-Z0-9]{1}([-a-zA-Z0-9_]{0,23})';
                        length 1..24 {
                            error-message "Invalid mirror session name";
                            error-app-tag session-name-invalid;
                        }
                    }
                    description
                        "Mirror session name.";
                }

                leaf src_ip {
                    type inet:ipv4-address;
                    description
                        "ERSPAN source ip. This IP will be set as source ip in
                        outer header of mirrored frame ";
                }

                leaf dst_ip {
                    type inet:ipv4-address;
                    description
                        "ERSPAN destination ip. Mirrored frames will be routed to this destination.
                        This IP will be set as destination ip in outer header of mirrored frame ";
                    sonic-ext:custom-validation ValidateDstIP;
                }

                leaf gre_type {
                    type string {
                        pattern "0[xX][0-9a-fA-F]*";
                        length 1..6 {
                            error-message "Invalid GRE type";
                            error-app-tag gre-type-invalid;
                        }
                    }
                    description
                        "ERSPAN GRE type. Mirrored frames will be sent with the configured GRE type";
                }

                leaf dscp {
                    type uint8 {
                        range "0..63" {
                            error-message "Invalid dscp value";
                            error-app-tag dscp-invalid;
                        }
                    }
                    description
                        "ERSPAN outer header DSCP value. Mirrored frames will be sent with configured DSCP value";
                }

                leaf ttl {
                    type uint8 {
                        range "0..63" {
                            error-message "Invalid TTL value";
                            error-app-tag ttl-invalid;
                        }
                    }
                    description
                        "ERSPAN outer header TTL value. Mirrored frames will be sent with configured TTL value";
                }

                leaf queue {
                    type uint8;
                    must "current() = 0" {
                        error-message "Invalid queue config. Queue 0 is only supported";
                        error-app-tag mirror-queue-not-supported;
                    }
                    description
                        "ERSPAN Queue. Mirrored frames will be sent to queue 0 only";
                }

                leaf dst_port {
                    type union{
                        type leafref {
                            path "/prt:sonic-port/prt:PORT/prt:PORT_LIST/prt:ifname";
                        }
                        type enumeration {
                            enum erspan;
                            enum CPU;
                        }
                    }
                    sonic-ext:custom-validation ValidateDstPort;
                    sonic-ext:custom-validation ValidateDstPortPacIntf;
                    description
                        "Destination port configuration for port mirroring(SPAN).
                        For ERSPAN session set as erspan,
                        For mirroring to CPU, set as CPU ";
                }

                leaf src_port {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                    sonic-ext:custom-validation ValidateSrcPort;
                    description
                        "Source port configuration for mirroring. Can be configured for both SPAN/ERSPAN.
                        Supports both port and port-channel as arguments";
                }

                leaf direction {
                    type enumeration {
                        enum RX;
                        enum TX;
                        enum BOTH;
                        enum rx;
                        enum tx;
                        enum both;
                    }
                    description
                        "Direction configuration for mirroring. Can be configured for both SPAN/ERSPAN.
                        Supports rx/tx/both as direction config.
                           RX: Captures frames ingressing on source port.
                           TX: Captures frames egressing on source port.
                           BOTH: Captures frames ingressing or egressing on source port.";
                }

                leaf type {
                    type enumeration {
                        enum span;
                        enum SPAN;
                        enum erspan;
                        enum ERSPAN;
                    }
                    description
                        "Mirror session type
                           span: port mirror session
                           erspan: ERSPAN session";
                }

                must "not (src_port) or not (dst_port) or (dst_port != src_port)" {
                    error-message "destination port cant be same as source port";
                    error-app-tag dst-port-same-as-src-port;
                }
            }
        }

        //state sonic mirror session table
        container MIRROR_SESSION_TABLE { 

            sonic-ext:db-name "STATE_DB"; 
            sonic-ext:key-delim "|"; 

            config false;
            description "state mirror session table";

            list MIRROR_SESSION_TABLE_LIST { 
                sonic-ext:db-name "STATE_DB"; 

                key "name";

                leaf name {
                    type string;
                    description
                        "Mirror session name.";
                }

                leaf status {
                    type string;
                    description
                        "Mirror session status. Valid valures are active/inactive/error
                        active: mirror session is active
                        inactive: mirror session is inactive when destination ip is not reachable in ERSPAN
                        error: configuration error";
                }

                leaf monitor_port {
                    type string;
                }

                leaf dst_mac {
                    type string;
                }

                leaf route_prefix {
                    type string;
                }

                leaf vlan_header_valid {
                    type uint32;
                }
            }
        }
    }
}
