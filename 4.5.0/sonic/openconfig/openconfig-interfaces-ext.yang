module openconfig-interfaces-ext {

    yang-version "1";

    // namespace
    namespace "http://openconfig.net/yang/interfaces/extension";

    prefix "oc-intf-ext";

    import openconfig-interfaces { prefix oc-intf; }
    import openconfig-vlan-types { prefix oc-vlan-types; }
    import openconfig-vlan { prefix oc-vlan; }
    import openconfig-if-ip {prefix oc-ip; }
    import openconfig-if-ip-ext {prefix oc-ip-ext; }
    import openconfig-if-ethernet {prefix oc-eth; }
    import openconfig-if-poe {prefix oc-poe; }
    import openconfig-inet-types { prefix oc-inet; }
    import openconfig-lacp {prefix oc-lacp; }
    import openconfig-if-tunnel {prefix oc-tun; }
    import openconfig-yang-types { prefix oc-yang; }
    import openconfig-types { prefix oc-types; }
    import openconfig-extensions { prefix oc-ext; }
    import ietf-inet-types { prefix "ietf-inet"; }
    import ietf-yang-types { prefix yang; }
    import openconfig-if-types-ext { prefix oc-if-types-ext; }
    import openconfig-inet-types-ext { prefix oc-inet-ext; }
    import openconfig-if-aggregate {prefix oc-lag; }

    organization "SONiC";

    contact
        "SONiC";

    description
        "This module contains collection of yang definitions for extensions to
         openconfig-interfaces yang";

    oc-ext:openconfig-version "1.0.3";

    revision "2024-12-12" {
        description
            "Add YANG extension for Bridge L2 Protocol Tunnel(L2PT) Configuration.";
        reference "1.0.3";
    }

    revision "2023-07-31" {
        description
            "Add YANG extension for VLAN translation.";
        reference "1.0.2";
    }

    revision "2021-11-08" {
        description
            "Add YANG extension for NDP.";
        reference "1.0.1";
    }

    revision "2020-06-02" {
        description
            "Updating the YANG with respect to RFC compliance";
        reference "1.0.0";
    }

    // typedef statements
    typedef if-status-type {
        type enumeration {
            enum OPER_UP {
                description
                "Interface is operationally up";
            }
            enum PHY_LINK_DOWN {
                description
                "Physical layer link is down";
            }
            enum ERR_DISABLED {
                description
                "The interface is error disabled by an application";
            }
            enum ADMIN_DOWN {
                description
                "The interface is administratively down making it operational down";
            }
            enum NO_TRANSCEIVER {
                description
                "The interface is down since transceiver is not present";
            }
        }
        description
            "Interface status";
    }

    typedef portchannel-status-type {
        type enumeration {
            enum OPER_UP {
                description
                "Portchannel is operationally up";
            }
            enum ALL_LINKS_DOWN {
                description
                "All the links in the portchannel are operationally down";
            }
            enum ERR_DISABLED {
                description
                "The portchannel is error disabled by an application";
            }
            enum LACP_FAIL {
                description
                "The LACP convergence failed for the portchannel members";
            }
            enum MIN_LINKS {
                description
                "The configured minimum links of the portchannel are not operationall UP";
            }
            enum ADMIN_DOWN {
                description
                "The portchannel is administartively down making it operational down";
            }
        }
        description
            "Portchannel status";
    }

    identity ND_ROUTER_PREFERENCE {
        description
            "router advertisement neighbor-discovery router-preference types";
    }

    identity HIGH {
        base "ND_ROUTER_PREFERENCE";
        description
            "neighbor-discovery router-preference type is high";
    }

    identity MEDIUM {
        base "ND_ROUTER_PREFERENCE";
        description
            "neighbor-discovery router-preference type is medium";
    }

    identity LOW {
        base "ND_ROUTER_PREFERENCE";
        description
            "neighbor-discovery router-preference type is low";
    }

    augment "/oc-intf:interfaces/oc-intf:interface/oc-eth:ethernet/oc-eth:state" {
        description "Interface down reason";

        leaf reason {
            type if-status-type;
            description "Interface status reason";
         }
    }

    augment "/oc-intf:interfaces/oc-intf:interface/oc-eth:ethernet" {
        description "Interface down reason";
        container reason-events {
            config false;
            description "Reason events.";
            list reason-event {
                description
                    "List of events that can cause interface to go down or up";
                container state {
                    description "Interface down reason event.";
                    leaf reason {
                        type if-status-type;
                        description "Interface status reason";
                    }
                    leaf event {
                        type string;
                        description
                        "Name of the event that may affect an interface to go down or up";
                    }
                    leaf timestamp {
                        type yang:date-and-time;
                        description
                        "Timestamp of interface up/down reason event.";
                    }
                }
            }
        }
    }

    augment "/oc-intf:interfaces/oc-intf:interface/oc-lag:aggregation/oc-lag:state" {
        description "Portchannel down reason";
        leaf reason {
            type portchannel-status-type;
            description "Portchannel status reason";
        }
    }

    augment "/oc-intf:interfaces/oc-intf:interface/oc-lag:aggregation" {
        description "Portchannel down reason";
        container reason-events {
            config false;
            description "Reason events.";
            list reason-event {
                description
                    "List of events that can cause portchannel to go down or up";
                container state {
                    description "Portchannel down reason event.";
                    leaf reason {
                        type portchannel-status-type;
                        description "Portchannel status reason";
                    }
                    leaf event {
                        type string;
                        description
                        "Name of the event that may affect an portchannel to go down or up";
                    }
                    leaf timestamp {
                        type string;
                        description
                        "Timestamp of portchannel up/down reason event.";
                    }
                }
            }
        }
    }

    augment "/oc-intf:interfaces/oc-intf:interface/oc-vlan:routed-vlan/oc-ip:ipv4/oc-ip:state/oc-ip:counters" {
        description "Additional byte and packet rates with counters container for routed vlan interface";
        uses interfaces-ext-rate-counters-state;
    }

    augment "/oc-intf:interfaces/oc-intf:interface/oc-vlan:routed-vlan/oc-ip:ipv6/oc-ip:state/oc-ip:counters" {
        description "Additional byte and packet rates with counters container for routed vlan interface";
        uses interfaces-ext-rate-counters-state;
    }

    augment "/oc-intf:interfaces/oc-intf:interface/oc-intf:subinterfaces/oc-intf:subinterface/oc-ip:ipv4/oc-ip:state/oc-ip:counters" {
        description "Additional byte and packet rates with counters container for routed sub-interface";
        uses interfaces-ext-rate-counters-state;
    }

    augment "/oc-intf:interfaces/oc-intf:interface/oc-intf:subinterfaces/oc-intf:subinterface/oc-ip:ipv6/oc-ip:state/oc-ip:counters" {
        description "Additional byte and packet rates with counters container for routed sub-interface";
        uses interfaces-ext-rate-counters-state;
    }

    grouping interfaces-ext-rate-counters-state {
        description "Interface state rate counters";
        leaf in-octets-per-second {
            type decimal64 {
                fraction-digits 2;
            }
            description
                "The total number of octets received per second on the interface";
        }
        leaf in-pkts-per-second {
            type decimal64 {
                fraction-digits 2;
            }
            description
                "The total number of packets received per second on the interface";
        }
        leaf in-bits-per-second {
            type decimal64 {
                fraction-digits 2;
            }
            description
                "The total number of bits received per second on the interface";
        }
        leaf in-utilization {
            type oc-types:percentage;
            description
                "RX utilization of the interface";
        }
        leaf out-octets-per-second {
            type decimal64 {
                fraction-digits 2;
            }
            description
                "The total number of octets transmitted per second on the interface";
        }
        leaf out-pkts-per-second {
            type decimal64 {
                fraction-digits 2;
            }
            description
                "The total number of packets transmitted per second on the interface";
        }
        leaf out-bits-per-second {
            type decimal64 {
                fraction-digits 2;
            }
            description
                "The total number of bits transmitted per second on the interface";
        }
        leaf out-utilization {
            type oc-types:percentage;
            description
                "TX utilization of the interface";
        }
}

    augment "/oc-intf:interfaces/oc-intf:interface/oc-eth:ethernet/oc-eth:state/oc-eth:counters" {
        description "Fast Link Failover counters container for physical interface";
        uses interfaces-ext-flf-counters-state;
    }

    grouping interfaces-ext-flf-counters-state {
        description "Interface flf counters";
        leaf hw-protection-switchover-events {
            type oc-yang:counter64;
            description
                "The total number of hardware protection group switch/Failover events";
        }
        leaf hw-protection-switchover-drop-pkts {
            type oc-yang:counter64;
            description
                "The total number of times when Primary and Secondary NextHop selections are down";
        }
    }

    grouping interfaces-ext-interface-sag-ipv4-config {
        description
            "IPv4 static anycast gateway config";

        leaf-list static-anycast-gateway {
            type ietf-inet:ipv4-prefix;
            max-elements 16;

            description
                "IPv4 static anycast gateway addresses";
        }
    }

    grouping interfaces-ext-interface-sag-ipv4-top {
        description
            "IPv4 static anycast gateway";

        container sag-ipv4 {
            description "Config and state parameters associated with sag-ipv4";

            container config {
                uses interfaces-ext-interface-sag-ipv4-config;

                description
                    "IPv4 static anycast gateway config";
            }
            container state {
                config false;
                uses interfaces-ext-interface-sag-ipv4-config;

                description
                    "IPv4 static anycast gateway state";
            }

        }
    }

    grouping interfaces-ext-interface-sag-ipv6-config {
        description
        "IPv6 static anycast gateway config";

        leaf-list static-anycast-gateway {

                  type ietf-inet:ipv6-prefix;
                  max-elements 16;

            description
                "IPv6 static anycast gateway addresses";

        }
    }

    grouping interfaces-ext-interface-sag-ipv6-top {
    description
        "IPv6 static anycast gateway";

        container sag-ipv6 {
            description "Config and state parameters associated with sag-ipv6";

            container config {
                uses interfaces-ext-interface-sag-ipv6-config;

                description
                    "IPv6 static anycast gateway config";
            }
            container state {
                config false;
                uses interfaces-ext-interface-sag-ipv6-config;

                description
                    "IPv6 static anycast gateway state";
            }

        }
    }

    grouping interfaces-ext-interface-vrrp-track-increment {

        description
            "List of track interfaces for VRRP";

        container vrrp-track {
            description
                "Configuration and state parameters relating to VRRP track interface";

        list vrrp-track-interface {
            key "track-intf";
            description
                "List of track interface";

            leaf track-intf {

                type leafref {
                    path "../config/track-intf";
                }
                description
                    "Reference to the list of interfaces";
            }

            container config {
                description
                    "Configuration data for each track interface";

                leaf track-intf {
                    type string;
                    description
                        "Reference to the list of interfaces";
                }

                leaf priority-increment {
                    type uint8 {
                        range "0..254";
                    }
                    description
                        "priority increment upon interface up";
                }
            }

            container state {
                config false;
                description
                    "Operational data for each track interface";

                leaf track-intf {
                    type string;
                    description
                        "Reference to the list of interfaces";
                }

                leaf priority-increment {
                    type uint8 {
                        range "0..254";
                    }
                    description
                        "priority increment upon interface up";
                }
            }

        }
        }

    }

    grouping interfaces-ext-interface-ipv6-nd-prefix-config {
        description
            "Configuring the IPv6 prefix to include in router advertisements.";

        leaf prefix {
            type oc-inet:ipv6-prefix;
            description 
                "Configuring the IPv6 prefix to include in router advertisements."; 
        }
        
        leaf valid-lifetime {
            type uint32 {
                range "0..4294967295";
            }
            units seconds;
            description
                "Valid lifetime in seconds"; 
            }

        leaf preferred-lifetime {
            type uint32 {
                range "0..4294967295";
            }
            units seconds;
            description
                "Preferred lifetime in seconds"; 
            }

        leaf no-autoconfig {
            type boolean;
            description 
                "indicates to hosts on the local link that the specified prefix 
                cannot be used for IPv6 autoconfiguration Default: not set, i.e. 
                prefix can be used for autoconfiguration";
            }

        leaf off-link {
            type boolean;
            description 
                "indicates that advertisement makes no statement about on-link or off-link 
                properties of the prefix. Default: not set, i.e. this prefix can 
                be used for on-link determination."; 
            }

        leaf router-address {
            type boolean;
            description 
                "indicates to hosts on the local link that the specified prefix contains 
                a complete IP address by setting R flag. Default: not set, i.e. hosts do 
                not assume a complete IP address is placed."; 
            }
    }

    grouping interfaces-ext-interface-ipv6-nd-prefix-top {
        description
            "IPv6 prefix to include in router advertisements top container";

        container ra-prefixes {
            description
                "Container enclosing IPv6 prefix to include in router advertisements configuration";

            list ra-prefix {
                key "prefix";

                description
                    "List of ra prefix addresses";

                leaf prefix {
                    type leafref {
                        path ../config/prefix;
                    }

                description
                    "ra prefix address";
                }

                /*leaf mask {
                    type leafref {
                        path ../config/mask;
                    }

                description
                    "ra prefix mask";
                }*/

                container config {
                    description
                        "ra prefix config";

                    uses interfaces-ext-interface-ipv6-nd-prefix-config;
                }

                container state {
                    config false;

                    description
                        "ra prefix operational state";

                    uses interfaces-ext-interface-ipv6-nd-prefix-config;
                }

            }
        }
    }

    grouping interfaces-ext-interface-ipv6-nd-rdnss-config {
        description
            "Recursive DNS server address config";

        leaf address {
            type oc-inet:ipv6-address;
            description "Recursive DNS server address to advertise using the RDNSS 
                        (type 25) option described in RFC8106. Can be specified more than once to 
                        advertise multiple addresses. Note that hosts may choose to limit the 
                        number of RDNSS addresses to track."; 
            }

        leaf valid-lifetime {
            type uint32 {
                range "0..4294967295";
            }
            units seconds;
            description
                "Valid lifetime in seconds"; 
            }
    }

    grouping interfaces-ext-interface-ipv6-nd-rdnss-top {
        description
            "Recursive DNS server address top container";

        container rdnss-addresses {
            description
                "Container enclosing all classifiers configuration";

            list rdnss-address {
                key "address";

                description
                    "List of rdnss addresses";

                leaf address {
                    type leafref {
                        path ../config/address;
                    }

                description
                    "rdnss address";
                }

                container config {
                    description
                        "rdnss config";

                    uses interfaces-ext-interface-ipv6-nd-rdnss-config;
                }

                container state {
                    config false;

                    description
                        "rdnss operational state";

                    uses interfaces-ext-interface-ipv6-nd-rdnss-config;
                }

            }
        }
    }


    grouping interfaces-ext-interface-ipv6-nd-dnssl-config {
        description
            "DNS server search name config";

        leaf dnssl-name {
            type string;
            description "Advertise DNS search list using the DNSSL (type 31) option 
                        described in RFC8106. Specify more than once to advertise 
                        multiple domain name suffixes. Host implementations may limit 
                        the number of honored search list entries."; 
            }

        leaf valid-lifetime {
            type uint32 {
                range "0..4294967295";
            }
            units seconds;
            description
                "Valid lifetime in seconds"; 
            }
    }

    grouping interfaces-ext-interface-ipv6-nd-dnssl-top {
        description
            "DNS server search name top container";

        container dns-search-names {
            description
                "Container enclosing all dns search names configuration";

            list dns-search-name {
                key "dnssl-name";

                description
                    "List of dns search names";

                leaf dnssl-name {
                    type leafref {
                        path ../config/dnssl-name;
                    }

                description
                    "dns search name";
                }

                container config {
                    description
                        "dns search name config";

                    uses interfaces-ext-interface-ipv6-nd-dnssl-config;
                }

                container state {
                    config false;

                    description
                        "dnssl operational state";

                    uses interfaces-ext-interface-ipv6-nd-dnssl-config;
                }

            }
        }
    }


    grouping interfaces-ext-interface-ipv6-nd-config {
        description "Neighbor advertisement related configuration for ipv6 interface ";
        leaf ra-retrans-interval {
            type uint32 {
                range "0..4294967295";
            }
            units milliseconds;
            description
                "The value to be placed in the Retrans Timer field in the Router
                Advertisement messages sent by the router.  The value zero means
                unspecified (by this router)";
            }

        leaf ra-interval-msec {
            type uint32 {
                range "70..1800000"; 
            }
            units milliseconds;
            description
                "The maximum time allowed between sending unsolicited multicast router 
                advertisements from the interface, in milliseconds. ";
            }

        leaf min-ra-interval {
            type uint32 {
                range "1..1350";
            }
            units seconds;
            description
                "The minimum time allowed between sending unsolicited multicast router
                advertisements from the interface, in seconds. ";
            }

        leaf min-ra-interval-msec {
            type uint32 {
                range "30..1350000";
            }
            units milliseconds;
            description
                "The minimum time allowed between sending unsolicited multicast router
                advertisements from the interface, in milliseconds. ";
            }

        leaf ra-hop-limit {
            type uint8 {
                range "0..255";
            }
            description
                "The value to be placed in the hop count field of router advertisements 
                sent from the interface, in hops. Indicates the maximum diameter of the 
                network. Setting the value to zero indicates that the value is 
                unspecified by this router.  ";
            }

        leaf reachable-time {
            type uint32 {
                range "0..3600000";
            }
            units milliseconds;
            description
                "The value to be placed in the Reachable Time field in the Router Advertisement 
                 messages sent by the router, in milliseconds. The configured time enables the 
                 router to detect unavailable neighbors. ";
            }

        leaf home-agent-preference {
            type uint16 {
                range "0..65535";
            }
            description
                "The value to be placed in Home Agent Option, when Home Agent config flag is set, 
                which indicates to hosts Home Agent preference. The default value of 0 stands for 
                the lowest preference possible. ";
            }

        leaf home-agent-lifetime {
            type uint16 {
                range "0..65520"; 
            }
            description
                "The value to be placed in Home Agent Option, when Home Agent config flag is set, 
                which indicates to hosts Home Agent Lifetime. The default value of 0 means to 
                place the current Router Lifetime value.";
            }

        leaf mtu {
            type uint32 {
                range "0..65535";
            }
            description
                "Include an MTU (type 5) option in each RA packet to assist the attached hosts in 
                proper interface configuration. The announced value is not verified to be 
                consistent with router interface MTU.";
            }
        
        leaf router-preference {
            type identityref {
                base "ND_ROUTER_PREFERENCE";
            }
            description
                "Set default router preference in IPv6 router advertisements per RFC4191. Default: medium"; 
            }

        leaf ra-fast-retrans {
            type boolean;
            description "When enabled, allows faster transmissions of RA packets in 
                        order to speed";
            }

        leaf managed-config {
            type boolean;
            description "Set/unset flag in IPv6 router advertisements which indicates 
                        to hosts that they should use managed (stateful) protocol for 
                        addresses autoconfiguration in addition to any addresses 
                        autoconfigured using stateless address autoconfiguration";
            }

        leaf other-config {
            type boolean;
            description "Set/unset flag in IPv6 router advertisements which indicates to 
                        hosts that they should use administered (stateful) protocol to 
                        obtain autoconfiguration information other than addresses";
            }

        leaf home-agent-config {
            type boolean;
            description "Set/unset flag in IPv6 router advertisements which indicates to 
                        hosts that the router acts as a Home Agent and includes a Home Agent Option";
            }

        leaf adv-interval-option {
            type boolean;
            description "Include an Advertisement Interval option which indicates to hosts 
                        the maximum time, in milliseconds, between successive unsolicited 
                        Router Advertisements";
            }
    }

    typedef matched-vlan-stack-action {
      type enumeration {
        enum PUSH {
          description
            "Push a VLAN onto the VLAN stack.";
        }
        enum POP {
          description
            "Pop a VLAN from the VLAN stack.";
        }
        enum SWAP {
          description
            "Swap the VLAN at the top of the VLAN stack.";
        }
        // TODO: add push-push, pop-pop, push-swap etc
      }
      description
        "Operations that can be performed on a VLAN stack.";
    }

    grouping vlan-logical-single-tagged-config {
      description
        "Specifies single-tagged packets with an exact VLAN identifier.";
  
      leaf-list vlan-ids {
      description
        "Match single-tagged packets with an exact VLAN identifier, 
         a list of VLAN identifiers or a range of VLAN identifiers.";

        type union {
          type oc-vlan-types:vlan-id;
          type oc-vlan-types:vlan-range;
        }
      }
    }

    grouping vlan-logical-double-tagged-config {
      description
        "Specifies double-tagged packets with inner exact and outer exact
         VLAN identifiers.";
  
      leaf inner-vlan-id {
        type oc-vlan-types:vlan-id;
        description
          "Inner VLAN identifier for double-tagged packets.";
      }
  
      leaf outer-vlan-id {
        type oc-vlan-types:vlan-id;
        description
          "Outer VLAN identifier for double-tagged packets.";
      }
    }

    grouping double-tagged-config {
      description
        "Specifies double-tagged packets with inner exact and outer exact
         VLAN identifiers.";
  
      leaf inner-vlan {
        type oc-vlan-types:vlan-id;
        description
          "Inner VLAN identifier for double-tagged packets.";
      }
  
      leaf outer-vlan {
        type oc-vlan-types:vlan-id;
        description
          "Outer VLAN identifier for double-tagged packets.";
      }
      leaf priority {
        type uint8 {
          range "0..7"{
            error-app-tag invalid-mapped-vlan-priority;
            error-message "Invalid mapped-vlan-priority Value.";
          }
        }
        description "priority for SVLAN";
      }
    }

    grouping single-tagged-config {
      description
        "Specifies single-tagged packets with outer exact
         VLAN identifiers.";
  
      leaf outer-vlan {
        type oc-vlan-types:vlan-id;
        description
          "Outer VLAN identifier for single-tagged packets.";
      }
      leaf priority {
        type uint8 {
          range "0..7"{
            error-app-tag invalid-mapped-vlan-priority;
            error-message "Invalid mapped-vlan-priority Value.";
          }
        }
        description "priority for SVLAN";
      }
    }

    grouping vlan-logical-match-top {
      description
        "Configuration for various VLAN tag matching schemes,
         including Q-in-Q.";
  
      container match {
        description
          "Configuration for various VLAN tag matching schemes,
           including single-tagged 802.1q packets and double-tagged
           802.1ad 'Q-in-Q' packets. Typically only one of the subordinate
           containers should be specified.";

        container single-tagged {
            description
              "Match single-tagged packets with an exact VLAN identifier, 
               a list of VLAN identifiers or a range of VLAN identifiers.";
  
            container config {
              description
                "Configuration for match single-tagged packets with an exact 
                 VLAN identifier, a list of VLAN identifiers or a range of 
                 VLAN identifiers.";
   
              uses vlan-logical-single-tagged-config;
            }
  
            container state {
              config false;
              description
                "Operational state for match single-tagged packets with an exact 
                 VLAN identifier, a list of VLAN identifiers or a range of 
                 VLAN identifiers.";

              uses vlan-logical-single-tagged-config;
            }
        }

        container double-tagged {
          description
            "Match double-tagged packets against inner exact and outer exact
             VLAN identifiers.";
  
          container config {
            description
              "Configuration for matching double-tagged packets against inner
               exact and outer exact VLAN identifiers.";
            uses vlan-logical-double-tagged-config;
          }
          container state {
            config false;
            description
              "State for matching double-tagged packets against inner exact
               and outer exact VLAN identifiers.";
            uses vlan-logical-double-tagged-config;
          }
        }
        container match-double-tags {
            description  "Double tagged VLAN translation";
            list match-double-tag {
                key "outer-vlan inner-vlan";
                description "Match double tags";
                leaf outer-vlan {
                    type leafref {
                        path "../config/outer-vlan";
                    }
                    description "outer VLAN";
                }
                leaf inner-vlan {
                    type leafref {
                        path "../config/inner-vlan";
                    }
                    description "inner VLAN";
                }
                container config {
                    description
                    "Configuration for matching double-tagged packets against inner
                    exact and outer exact VLAN identifiers.";
                    uses double-tagged-config;
                }
                container state {
                    config false;
                    description
                    "State for matching double-tagged packets against inner exact
                    and outer exact VLAN identifiers.";
                    uses double-tagged-config;
                }
            }
        }
        container match-single-tags {
            description  "Single tagged VLAN translation";
            list match-single-tag {
                key "outer-vlan";
                description "Match single tags";
                leaf outer-vlan {
                    type leafref {
                        path "../config/outer-vlan";
                    }
                    description "outer VLAN";
                }
                container config {
                    description
                    "Configuration for matching single-tagged packets against
                     outer exact VLAN identifiers.";
                    uses single-tagged-config;
                }
                container state {
                    config false;
                    description
                    "State for matching single-tagged packets against 
                     outer exact VLAN identifiers.";
                    uses single-tagged-config;
                }
            }
        }
      }
    }

    grouping vlan-logical-ingress-mapping-config {
      description
        "Configuration for ingress VLAN stack behaviors for
         packets that arrive on this subinterface.";

      leaf vlan-stack-action {
        type matched-vlan-stack-action;
        description
          "The action to take on the VLAN stack of a packet. This is
           optionally used in conjunction with adjacent leaves to override
           the values of the action.";
      }
      leaf mapped-vlan-priority {
        type uint8 {
          range "0..7"{
            error-app-tag invalid-mapped-vlan-priority;
            error-message "Invalid mapped-vlan-priority Value.";
          }
        }
       
        description 
        "IEEE 802 Priority Code Point(PCP) carried by mapped vlan. The value denotes class of service.";
        }
    }

    grouping vlan-logical-ingress-mapping-top {
      description
        "Ingress VLAN stack behaviors for packets that arrive on
         this subinterface after their VLAN idenitifer(s) have been
         matched.";

      container ingress-mapping {
        description
          "Ingress VLAN stack behaviors for packets that arrive on
           this subinterface after their VLAN idenitifer(s) have been
           matched.";

        container config {
          description
            "Configuration for ingress VLAN and label behaviors for
             packets that arrive on this subinterface after their VLAN
             identifier(s) have been matched.";

          uses vlan-logical-ingress-mapping-config;
        }
        container state {
          config false;
          description
            "State for ingress VLAN and label behaviors for packets
             that arrive on this subinterface.";

          uses vlan-logical-ingress-mapping-config;
        }
      }
    }

    grouping vlan-logical-egress-mapping-config {
      description
        "Configuration for egress VLAN stack behaviors for
         packets that are destined for output via this subinterface.";

      leaf vlan-stack-action {
        type matched-vlan-stack-action;
        description
          "The action to take on the VLAN stack of a packet. This is
           optionally used in conjunction with adjacent leaves to override
           the values of the action.";
      }

      leaf mapped-vlan-priority {
        type uint8 {
          range "0..7"{
            error-app-tag invalid-mapped-vlan-priority;
            error-message "Invalid mapped-vlan-priority Value.";
          }
        }

        description 
          "IEEE 802 Priority Code Point(PCP) carried by mapped vlan. The value denotes class of service.";
        }
    }

    grouping vlan-logical-egress-mapping-top {
      description
        "Egress VLAN stack behaviors for packets that are
         destined for output via this subinterface.";

      container egress-mapping {
        description
          "Egress VLAN and label behaviors for packets that are
           destined for output via this subinterface.";

        container config {
          description
            "Configuration for egress VLAN stack behaviors for
             packets that are destined for output via this subinterface.";

          uses vlan-logical-egress-mapping-config;
        }
        container state {
          config false;
          description
            "State for engress VLAN stack behaviors for packets
             that are destined for output via this subinterface.";

          uses vlan-logical-egress-mapping-config;
        }
      }
    }

    grouping mapped-vlan-config {
      description
        "VLAN related configuration that is mapped based on 
         mapping rules.";

      leaf vlan-id {
        type oc-vlan-types:vlan-id;
        description
          "VLAN id mapped based on mapping rules.";

      }
      leaf multi-tag {
        type boolean;
        description
            "Supports multitag(max 3 tag) traffic if true when SVLAN is mapped to VXLAN";
      }
    }

    grouping mapped-vlan-state {
      description
        "VLAN related operational state that is mapped based on 
         mapping rules.";

      //TODO: placeholder to add VLAN-specific state variables on
      //the subinterface
    }

    grouping interfaces-ext-vlan-matching-mapping-action-rules {
        description
          "Top-level grouping for VLAN stack matching and 
          mapping rules associated with a physical interface 
          or a portchannel.";

        container mapped-vlans {
            description
                "Enclosing container for mapping VLANs on 
                subinterfaces";

            list mapped-vlan {
                key "vlan-id";

                description "Configured mapping VLANs keyed by id";

                leaf vlan-id {
                    type leafref {
                        path "../config/vlan-id";
                    }
                        description "references the configured vlan-id";
                }

                container config {
                    description "Configuration parameters for VLANs";

                    uses mapped-vlan-config;
                }

                container state {
                    config false;
                        description "State variables for VLANs";

                    uses mapped-vlan-config;
                    uses mapped-vlan-state;
                }

                uses vlan-logical-match-top;
                uses vlan-logical-ingress-mapping-top;
                uses vlan-logical-egress-mapping-top;
            }
        }
    }

    grouping interfaces-ext-interface-ipv6-nd-state {
        description "Neighbor advertisement related state for ipv6 interface ";
        leaf ra-pkt-sent {
            type uint32; 
            description
                "Router Advertisement packets sent on this interface";
            }
        leaf ra-pkt-rcvd {
            type uint32; 
            description
                "Router Advertisement packets received on this interface";
            }
    }

    typedef l2pt-protocol {
        type enumeration {
            enum "LLDP" {
                description "Link Layer Discovery Protocol";
            }
            enum "LACP" {
                description "Link Aggregation Control Protocol";
            }
            enum "STP" {
                description "Spanning Tree Protocol";
            }
            enum "CDP" {
                description "Cisco Discovery Protocol";
            }
        }
        description "Enumeration of Layer 2 protocols for tunneling";
    }

    grouping interfaces-ext-bridge-l2pt-config {
        description
            "Top level grouping for Bridge L2 Protocol Tunnel configuration";
        leaf protocol {
            description "Layer 2 protocol to tunnel";
            type l2pt-protocol;
        }
        leaf-list vlan-ids {
            description "VLAN ID or range of VLAN IDs for the interface
                         on the layer 2 protocol packets to be tunneled";
            type union {
                type oc-vlan-types:vlan-id;
                type oc-vlan-types:vlan-range;
           }
        }
    }
    grouping interfaces-ext-bridge-l2pt-top {
        description
            "Top level grouping for Bridge L2 Protocol Tunnel(L2PT) configuration
             on a Physical Interface";
        container bridge-l2pt-params {
            list bridge-l2pt-param {
                key "protocol";
                description "List of L2PT configurations per interface and Vlan";
                leaf protocol {
                    type leafref {
                        path "../config/protocol";
                    }
                    description "Reference to the L2PT protocol";
                }
                container config {
                    description "Configuration data for L2PT";
                    uses interfaces-ext-bridge-l2pt-config;
                }
                container state {
                    config false;
                    description "State data for L2PT";
                    uses interfaces-ext-bridge-l2pt-config;
                }
            }
            description "Top level container for L2PT Configuration";
        }
    }

    augment "/oc-intf:interfaces/oc-intf:interface/oc-vlan:routed-vlan/oc-ip:ipv6/oc-ip:router-advertisement" {
        description
            "Recursive DNS server, dnssl and prefix related configuration for ipv6 router advertisement.";
        uses interfaces-ext-interface-ipv6-nd-rdnss-top;
        uses interfaces-ext-interface-ipv6-nd-dnssl-top;
        uses interfaces-ext-interface-ipv6-nd-prefix-top;
    }

    augment "/oc-intf:interfaces/oc-intf:interface/oc-vlan:routed-vlan/oc-ip:ipv6/oc-ip:router-advertisement/oc-ip:config" {
        description
            "Neighbor advertisement related configuration for ipv6 router advertisement.";
        uses interfaces-ext-interface-ipv6-nd-config;
    }

    augment "/oc-intf:interfaces/oc-intf:interface/oc-vlan:routed-vlan/oc-ip:ipv6/oc-ip:router-advertisement/oc-ip:state" {
        description
            "Neighbor advertisement related state for ipv6 router advertisement.";
        uses interfaces-ext-interface-ipv6-nd-config;
        uses interfaces-ext-interface-ipv6-nd-state;
    }


  augment "/oc-intf:interfaces/oc-intf:interface/oc-vlan:routed-vlan/oc-ip:ipv4" {
        description
            "SAG config and state data.";
        uses interfaces-ext-interface-sag-ipv4-top {
      when "oc-intf:config/oc-intf:type = 'oc-if-types-ext:IF_NVE'";
      description
          "SAG interface config/state";
      }
  }

  augment "/oc-intf:interfaces/oc-intf:interface/oc-intf:subinterfaces/oc-intf:subinterface/oc-ip:ipv4" {
        description
            "SAG config and state data.";
        uses interfaces-ext-interface-sag-ipv4-top {
      when "oc-intf:config/oc-intf:type = 'oc-if-types-ext:IF_NVE'";
      description
          "SAG interface config/state";
      }
  }

    augment "/oc-intf:interfaces/oc-intf:interface/oc-vlan:routed-vlan/oc-ip:ipv6" {
        description
            "SAG config and state data.";
        uses interfaces-ext-interface-sag-ipv6-top {
      when "oc-intf:config/oc-intf:type = 'oc-if-types-ext:IF_NVE'";
            description
              "SAG interface config/state";
        }
    }

  augment "/oc-intf:interfaces/oc-intf:interface/oc-intf:subinterfaces/oc-intf:subinterface/oc-ip:ipv6" {
        description
            "SAG config and state data.";
        uses interfaces-ext-interface-sag-ipv6-top {
      when "oc-intf:config/oc-intf:type = 'oc-if-types-ext:IF_NVE'";
            description
              "SAG interface config/state";
        }
    }

    augment "/oc-intf:interfaces/oc-intf:interface/oc-intf:subinterfaces/oc-intf:subinterface/oc-ip:ipv4/oc-ip:addresses/oc-ip:address/oc-ip:vrrp/oc-ip:vrrp-group/oc-ip:config" {
        description
            "VRRP IPv4 config version";
        leaf version {
            type uint8 {
                range "2..3";
            }
            description
                "version";
        }
    }

    augment "/oc-intf:interfaces/oc-intf:interface/oc-intf:subinterfaces/oc-intf:subinterface/oc-ip:ipv4/oc-ip:addresses/oc-ip:address/oc-ip:vrrp/oc-ip:vrrp-group/oc-ip:state" {
        description
            "VRRP IPv4 state version";
        leaf version {
            type uint8 {
                range "2..3";
            }
            description
                "version";
        }
    }

    augment "/oc-intf:interfaces/oc-intf:interface/oc-intf:subinterfaces/oc-intf:subinterface/oc-ip:ipv4/oc-ip:addresses/oc-ip:address/oc-ip:vrrp/oc-ip:vrrp-group/oc-ip:config" {
        description
            "VRRP IPv4 config use version 2 checksum";
        leaf use-v2-checksum {
            type boolean;
            description
                "Use version 2 checksum";
        }
    }

    augment "/oc-intf:interfaces/oc-intf:interface/oc-intf:subinterfaces/oc-intf:subinterface/oc-ip:ipv4/oc-ip:addresses/oc-ip:address/oc-ip:vrrp/oc-ip:vrrp-group/oc-ip:state" {
        description
            "VRRP IPv4 config use version 2 checksum";
        leaf use-v2-checksum {
            type boolean;
            description
                "Use version 2 checksum";
        }
    }

    augment "/oc-intf:interfaces/oc-intf:interface/oc-intf:subinterfaces/oc-intf:subinterface/oc-ip:ipv4/oc-ip:addresses/oc-ip:address/oc-ip:vrrp/oc-ip:vrrp-group/oc-ip:state" {
        description
            "VRRP IPv4 MASTER state";
        leaf status {
            type uint8 {
                range "0..2";
            }
            description
                "status";
        }
    }

    augment "/oc-intf:interfaces/oc-intf:interface/oc-intf:subinterfaces/oc-intf:subinterface/oc-ip:ipv6/oc-ip:addresses/oc-ip:address/oc-ip:vrrp/oc-ip:vrrp-group/oc-ip:state" {
        description
            "VRRP IPv6 state version";
        leaf version {
            type uint8 {
                range "2..3";
            }
            description
                "version";
        }
    }

    augment "/oc-intf:interfaces/oc-intf:interface/oc-intf:subinterfaces/oc-intf:subinterface/oc-ip:ipv6/oc-ip:addresses/oc-ip:address/oc-ip:vrrp/oc-ip:vrrp-group/oc-ip:state" {
        description
            "VRRP IPv6 MASTER state";
        leaf status {
            type uint8 {
                range "0..2";
            }
            description
                "status";
        }
    }

    augment "/oc-intf:interfaces/oc-intf:interface/oc-vlan:routed-vlan/oc-ip:ipv4/oc-ip:addresses/oc-ip:address/oc-ip:vrrp/oc-ip:vrrp-group/oc-ip:config" {
        description
            "VRRP IPv4 config version";
        leaf version {
            type uint8 {
                range "2..3";
            }
            description
                "version";
        }
    }

    augment "/oc-intf:interfaces/oc-intf:interface/oc-vlan:routed-vlan/oc-ip:ipv4/oc-ip:addresses/oc-ip:address/oc-ip:vrrp/oc-ip:vrrp-group/oc-ip:state" {
        description
            "VRRP IPv4 state version";
        leaf version {
            type uint8 {
                range "2..3";
            }
            description
                "version";
        }
    }

    augment "/oc-intf:interfaces/oc-intf:interface/oc-vlan:routed-vlan/oc-ip:ipv4/oc-ip:addresses/oc-ip:address/oc-ip:vrrp/oc-ip:vrrp-group/oc-ip:config" {
        description
            "VRRP IPv4 config use version 2 checksum";
        leaf use-v2-checksum {
            type boolean;
            description
                "Use version 2 checksum";
        }
    }

    augment "/oc-intf:interfaces/oc-intf:interface/oc-vlan:routed-vlan/oc-ip:ipv4/oc-ip:addresses/oc-ip:address/oc-ip:vrrp/oc-ip:vrrp-group/oc-ip:state" {
        description
            "VRRP IPv4 config use version 2 checksum";
        leaf use-v2-checksum {
            type boolean;
            description
                "Use version 2 checksum";
        }
    }

    augment "/oc-intf:interfaces/oc-intf:interface/oc-vlan:routed-vlan/oc-ip:ipv4/oc-ip:addresses/oc-ip:address/oc-ip:vrrp/oc-ip:vrrp-group/oc-ip:state" {
        description
            "VRRP IPv4 MASTER state";
        leaf status {
            type uint8 {
                range "0..2";
            }
            description
                "status";
        }
    }

    augment "/oc-intf:interfaces/oc-intf:interface/oc-vlan:routed-vlan/oc-ip:ipv6/oc-ip:addresses/oc-ip:address/oc-ip:vrrp/oc-ip:vrrp-group/oc-ip:state" {
        description
            "VRRP IPv6 state version";
        leaf version {
            type uint8 {
                range "2..3";
            }
            description
                "version";
        }
    }

    augment "/oc-intf:interfaces/oc-intf:interface/oc-vlan:routed-vlan/oc-ip:ipv6/oc-ip:addresses/oc-ip:address/oc-ip:vrrp/oc-ip:vrrp-group/oc-ip:state" {
        description
            "VRRP IPv6 MASTER state";
        leaf status {
            type uint8 {
                range "0..2";
            }
            description
                "status";
        }
    }

    deviation "/oc-intf:interfaces/oc-intf:interface/oc-vlan:routed-vlan/oc-ip:ipv6/oc-ip:neighbors/oc-ip:neighbor/oc-ip:state/oc-ip:ip" {
        deviate replace {
            type oc-inet-ext:ipv6-address-ext;
        }
    }

    deviation "/oc-intf:interfaces/oc-intf:interface/oc-intf:subinterfaces/oc-intf:subinterface/oc-ip:ipv6/oc-ip:neighbors/oc-ip:neighbor/oc-ip:state/oc-ip:ip" {
        deviate replace {
            type oc-inet-ext:ipv6-address-ext;
        }
    }

    augment "/oc-intf:interfaces/oc-intf:interface/oc-intf:subinterfaces/oc-intf:subinterface/oc-ip:ipv4/oc-ip:neighbors/oc-ip:neighbor/oc-ip:state" {
        description "Additional remote attribute for neighbor state";
        leaf remote {
            type uint8 {
                range "0..2";
            }
            description "Entry remote status";
        }
    }

    augment "/oc-intf:interfaces/oc-intf:interface/oc-intf:subinterfaces/oc-intf:subinterface/oc-ip:ipv6/oc-ip:neighbors/oc-ip:neighbor/oc-ip:state" {
        description "Additional remote attribute for neighbor state";
        leaf remote {
            type uint8 {
                range "0..2";
            }
            description "Entry remote status";
        }
    }


    augment "/oc-intf:interfaces/oc-intf:interface/oc-vlan:routed-vlan/oc-ip:ipv4/oc-ip:neighbors/oc-ip:neighbor/oc-ip:state" {
        description "Additional remote attribute for neighbor state";
        leaf remote {
            type uint8 {
                range "0..2";
            }
            description "Entry remote status";
        }
    }

    augment "/oc-intf:interfaces/oc-intf:interface/oc-vlan:routed-vlan/oc-ip:ipv6/oc-ip:neighbors/oc-ip:neighbor/oc-ip:state" {
        description "Additional remote attribute for neighbor state";
        leaf remote {
            type uint8 {
                range "0..2";
            }
            description "Entry remote status";
        }
    }

    augment "/oc-intf:interfaces/oc-intf:interface/oc-vlan:routed-vlan/oc-ip:ipv4/oc-ip:addresses/oc-ip:address/oc-ip:vrrp/oc-ip:vrrp-group" {
        description "Track interface priority for IPv4 VRRP instance";
        uses interfaces-ext-interface-vrrp-track-increment;
    }

    augment "/oc-intf:interfaces/oc-intf:interface/oc-vlan:routed-vlan/oc-ip:ipv6/oc-ip:addresses/oc-ip:address/oc-ip:vrrp/oc-ip:vrrp-group" {
        description "Track interface priority for IPv6 VRRP instance";
        uses interfaces-ext-interface-vrrp-track-increment;
    }

    augment "/oc-intf:interfaces/oc-intf:interface/oc-intf:subinterfaces/oc-intf:subinterface/oc-ip:ipv4/oc-ip:addresses/oc-ip:address/oc-ip:vrrp/oc-ip:vrrp-group" {
        description "Track interface priority for IPv4 VRRP instance";
        uses interfaces-ext-interface-vrrp-track-increment;
    }

    augment "/oc-intf:interfaces/oc-intf:interface/oc-intf:subinterfaces/oc-intf:subinterface/oc-ip:ipv6/oc-ip:addresses/oc-ip:address/oc-ip:vrrp/oc-ip:vrrp-group" {
        description "Track interface priority for IPv6 VRRP instance";
        uses interfaces-ext-interface-vrrp-track-increment;
    }

    augment "/oc-intf:interfaces/oc-intf:interface/oc-intf:subinterfaces/oc-intf:subinterface/oc-intf:config" {
        description "MTU";
        leaf mtu {
            type uint16;
            description "MTU";
        }
    }
    augment "/oc-intf:interfaces/oc-intf:interface/oc-intf:subinterfaces/oc-intf:subinterface/oc-intf:state" {
        description "MTU";
        leaf mtu {
            type uint16;
            description "MTU";
        }
    }

    augment "/oc-intf:interfaces/oc-intf:interface/oc-intf:subinterfaces/oc-intf:subinterface/oc-ip:ipv6/oc-ip:router-advertisement" {
        description
            "Recursive DNS server, dnssl and prefix related configuration for ipv6 router advertisement.";
        uses interfaces-ext-interface-ipv6-nd-rdnss-top;
        uses interfaces-ext-interface-ipv6-nd-dnssl-top;
        uses interfaces-ext-interface-ipv6-nd-prefix-top;
    }

    augment "/oc-intf:interfaces/oc-intf:interface/oc-intf:subinterfaces/oc-intf:subinterface/oc-ip:ipv6/oc-ip:router-advertisement/oc-ip:config" {
        description
            "Neighbor advertisement related configuration for ipv6 router advertisement.";
        uses interfaces-ext-interface-ipv6-nd-config;
    }

    augment "/oc-intf:interfaces/oc-intf:interface/oc-intf:subinterfaces/oc-intf:subinterface/oc-ip:ipv6/oc-ip:router-advertisement/oc-ip:state" {
        description
            "Neighbor advertisement related state for ipv6 router advertisement.";
        uses interfaces-ext-interface-ipv6-nd-config;
        uses interfaces-ext-interface-ipv6-nd-state;
    }

    augment "/oc-intf:interfaces/oc-intf:interface" {
        description
            "Vlan Stacking and translation match & action rules on a subinterface";
        uses interfaces-ext-vlan-matching-mapping-action-rules;
    }

    augment "/oc-intf:interfaces/oc-intf:interface" {
        when "not(oc-intf:type = 'iana-if-type:ieee8023adLag' and oc-intf:state/oc-intf:type = 'oc-ift:IF_AGGREGATE')";
        description
            "Bridge L2 Protocol Tunnel configuration on a Physical Interface";
        uses interfaces-ext-bridge-l2pt-top;
    }

    deviation /oc-intf:interfaces/oc-intf:interface/oc-vlan:routed-vlan/oc-ip:ipv4/oc-ip:config/oc-ip:dhcp-client {
        deviate not-supported;
    }

    deviation /oc-intf:interfaces/oc-intf:interface/oc-vlan:routed-vlan/oc-ip:ipv6/oc-ip:config/oc-ip:dhcp-client {
        deviate not-supported;
    }

    deviation /oc-intf:interfaces/oc-intf:interface/oc-vlan:routed-vlan/oc-ip:ipv4/oc-ip:state/oc-ip:dhcp-client {
        deviate not-supported;
    }

    deviation /oc-intf:interfaces/oc-intf:interface/oc-vlan:routed-vlan/oc-ip:ipv6/oc-ip:state/oc-ip:dhcp-client {
        deviate not-supported;
    }

    deviation /oc-intf:interfaces/oc-intf:interface/oc-intf:hold-time {
        deviate not-supported;
    }

    deviation /oc-intf:interfaces/oc-intf:interface/oc-intf:subinterfaces/oc-intf:subinterface/oc-ip:ipv4/oc-ip:addresses/oc-ip:address/oc-ip:vrrp/oc-ip:vrrp-group/oc-ip:config/oc-ip:preempt-delay {
        deviate not-supported;
    }

    deviation /oc-intf:interfaces/oc-intf:interface/oc-intf:subinterfaces/oc-intf:subinterface/oc-ip:ipv4/oc-ip:addresses/oc-ip:address/oc-ip:vrrp/oc-ip:vrrp-group/oc-ip:config/oc-ip:accept-mode {
        deviate not-supported;
    }

    deviation /oc-intf:interfaces/oc-intf:interface/oc-intf:subinterfaces/oc-intf:subinterface/oc-ip:ipv4/oc-ip:addresses/oc-ip:address/oc-ip:vrrp/oc-ip:vrrp-group/oc-ip:state/oc-ip:preempt-delay {
        deviate not-supported;
    }

    deviation /oc-intf:interfaces/oc-intf:interface/oc-intf:subinterfaces/oc-intf:subinterface/oc-ip:ipv4/oc-ip:addresses/oc-ip:address/oc-ip:vrrp/oc-ip:vrrp-group/oc-ip:state/oc-ip:accept-mode {
        deviate not-supported;
    }

    deviation /oc-intf:interfaces/oc-intf:interface/oc-intf:subinterfaces/oc-intf:subinterface/oc-ip:ipv4/oc-ip:addresses/oc-ip:address/oc-ip:vrrp/oc-ip:vrrp-group/oc-ip:interface-tracking/oc-ip:config/oc-ip:track-interface {
        deviate not-supported;
    }

    deviation /oc-intf:interfaces/oc-intf:interface/oc-intf:subinterfaces/oc-intf:subinterface/oc-ip:ipv4/oc-ip:addresses/oc-ip:address/oc-ip:vrrp/oc-ip:vrrp-group/oc-ip:interface-tracking/oc-ip:config/oc-ip:priority-decrement {
        deviate not-supported;
    }

    deviation /oc-intf:interfaces/oc-intf:interface/oc-intf:subinterfaces/oc-intf:subinterface/oc-ip:ipv4/oc-ip:addresses/oc-ip:address/oc-ip:vrrp/oc-ip:vrrp-group/oc-ip:interface-tracking/oc-ip:state/oc-ip:track-interface {
        deviate not-supported;
    }

    deviation /oc-intf:interfaces/oc-intf:interface/oc-intf:subinterfaces/oc-intf:subinterface/oc-ip:ipv4/oc-ip:addresses/oc-ip:address/oc-ip:vrrp/oc-ip:vrrp-group/oc-ip:interface-tracking/oc-ip:state/oc-ip:priority-decrement {
        deviate not-supported;
    }

    deviation /oc-intf:interfaces/oc-intf:interface/oc-vlan:routed-vlan/oc-ip:ipv4/oc-ip:addresses/oc-ip:address/oc-ip:vrrp/oc-ip:vrrp-group/oc-ip:config/oc-ip:preempt-delay {
        deviate not-supported;
    }

    deviation /oc-intf:interfaces/oc-intf:interface/oc-vlan:routed-vlan/oc-ip:ipv4/oc-ip:addresses/oc-ip:address/oc-ip:vrrp/oc-ip:vrrp-group/oc-ip:config/oc-ip:accept-mode {
        deviate not-supported;
    }

    deviation /oc-intf:interfaces/oc-intf:interface/oc-vlan:routed-vlan/oc-ip:ipv4/oc-ip:addresses/oc-ip:address/oc-ip:vrrp/oc-ip:vrrp-group/oc-ip:state/oc-ip:preempt-delay {
        deviate not-supported;
    }

    deviation /oc-intf:interfaces/oc-intf:interface/oc-vlan:routed-vlan/oc-ip:ipv4/oc-ip:addresses/oc-ip:address/oc-ip:vrrp/oc-ip:vrrp-group/oc-ip:state/oc-ip:accept-mode {
        deviate not-supported;
    }

    deviation /oc-intf:interfaces/oc-intf:interface/oc-vlan:routed-vlan/oc-ip:ipv4/oc-ip:addresses/oc-ip:address/oc-ip:vrrp/oc-ip:vrrp-group/oc-ip:interface-tracking/oc-ip:config/oc-ip:track-interface {
        deviate not-supported;
    }

    deviation /oc-intf:interfaces/oc-intf:interface/oc-vlan:routed-vlan/oc-ip:ipv4/oc-ip:addresses/oc-ip:address/oc-ip:vrrp/oc-ip:vrrp-group/oc-ip:interface-tracking/oc-ip:config/oc-ip:priority-decrement {
        deviate not-supported;
    }

    deviation /oc-intf:interfaces/oc-intf:interface/oc-vlan:routed-vlan/oc-ip:ipv4/oc-ip:addresses/oc-ip:address/oc-ip:vrrp/oc-ip:vrrp-group/oc-ip:interface-tracking/oc-ip:state/oc-ip:track-interface {
        deviate not-supported;
    }

    deviation /oc-intf:interfaces/oc-intf:interface/oc-vlan:routed-vlan/oc-ip:ipv4/oc-ip:addresses/oc-ip:address/oc-ip:vrrp/oc-ip:vrrp-group/oc-ip:interface-tracking/oc-ip:state/oc-ip:priority-decrement {
        deviate not-supported;
    }

    deviation /oc-intf:interfaces/oc-intf:interface/oc-intf:subinterfaces/oc-intf:subinterface/oc-ip:ipv4/oc-ip:config {
        deviate not-supported;
    }
    deviation /oc-intf:interfaces/oc-intf:interface/oc-intf:subinterfaces/oc-intf:subinterface/oc-ip:ipv4/oc-ip:state/oc-ip:mtu {
        deviate not-supported;
    }
    deviation /oc-intf:interfaces/oc-intf:interface/oc-intf:subinterfaces/oc-intf:subinterface/oc-ip:ipv4/oc-ip:state/oc-ip:enabled {
        deviate not-supported;
    }

    deviation /oc-intf:interfaces/oc-intf:interface/oc-intf:subinterfaces/oc-intf:subinterface/oc-ip:ipv6/oc-ip:config/oc-ip:enabled {
        deviate replace {
            default false;
        }
    }
    deviation /oc-intf:interfaces/oc-intf:interface/oc-vlan:routed-vlan/oc-ip:ipv6/oc-ip:config/oc-ip:enabled {
        deviate replace {
            default false;
        }
    }
    deviation /oc-intf:interfaces/oc-intf:interface/oc-intf:subinterfaces/oc-intf:subinterface/oc-ip:ipv6/oc-ip:config/oc-ip:mtu {
        deviate not-supported;
    }
    deviation /oc-intf:interfaces/oc-intf:interface/oc-intf:subinterfaces/oc-intf:subinterface/oc-ip:ipv6/oc-ip:state/oc-ip:mtu {
        deviate not-supported;
    }
    deviation /oc-intf:interfaces/oc-intf:interface/oc-intf:subinterfaces/oc-intf:subinterface/oc-ip:ipv6/oc-ip:config/oc-ip:dup-addr-detect-transmits {
        deviate not-supported;
    }
    deviation /oc-intf:interfaces/oc-intf:interface/oc-intf:subinterfaces/oc-intf:subinterface/oc-ip:ipv6/oc-ip:state/oc-ip:dup-addr-detect-transmits {
        deviate not-supported;
    }
    deviation /oc-intf:interfaces/oc-intf:interface/oc-intf:subinterfaces/oc-intf:subinterface/oc-ip:ipv6/oc-ip:config/oc-ip:dhcp-client {
        deviate not-supported;
    }

    deviation /oc-intf:interfaces/oc-intf:interface/oc-intf:subinterfaces/oc-intf:subinterface/oc-ip:ipv6/oc-ip:addresses/oc-ip:address/oc-ip:vrrp/oc-ip:vrrp-group/oc-ip:config/oc-ip:preempt-delay {
        deviate not-supported;
    }

    deviation /oc-intf:interfaces/oc-intf:interface/oc-intf:subinterfaces/oc-intf:subinterface/oc-ip:ipv6/oc-ip:addresses/oc-ip:address/oc-ip:vrrp/oc-ip:vrrp-group/oc-ip:config/oc-ip:accept-mode {
        deviate not-supported;
    }

    deviation /oc-intf:interfaces/oc-intf:interface/oc-intf:subinterfaces/oc-intf:subinterface/oc-ip:ipv6/oc-ip:addresses/oc-ip:address/oc-ip:vrrp/oc-ip:vrrp-group/oc-ip:state/oc-ip:preempt-delay {
        deviate not-supported;
    }

    deviation /oc-intf:interfaces/oc-intf:interface/oc-intf:subinterfaces/oc-intf:subinterface/oc-ip:ipv6/oc-ip:addresses/oc-ip:address/oc-ip:vrrp/oc-ip:vrrp-group/oc-ip:state/oc-ip:accept-mode {
        deviate not-supported;
    }

    deviation /oc-intf:interfaces/oc-intf:interface/oc-intf:subinterfaces/oc-intf:subinterface/oc-ip:ipv4/oc-ip:addresses/oc-ip:address/oc-ip:vrrp/oc-ip:vrrp-group/oc-ip:interface-tracking {
        deviate not-supported;
    }

    deviation /oc-intf:interfaces/oc-intf:interface/oc-intf:subinterfaces/oc-intf:subinterface/oc-ip:ipv6/oc-ip:addresses/oc-ip:address/oc-ip:vrrp/oc-ip:vrrp-group/oc-ip:interface-tracking {
        deviate not-supported;
    }

    deviation /oc-intf:interfaces/oc-intf:interface/oc-intf:subinterfaces/oc-intf:subinterface/oc-ip:ipv6/oc-ip:addresses/oc-ip:address/oc-ip:vrrp/oc-ip:vrrp-group/oc-ip:config/oc-ip:virtual-link-local {
        deviate not-supported;
    }

    deviation /oc-intf:interfaces/oc-intf:interface/oc-intf:subinterfaces/oc-intf:subinterface/oc-ip:ipv6/oc-ip:addresses/oc-ip:address/oc-ip:vrrp/oc-ip:vrrp-group/oc-ip:state/oc-ip:virtual-link-local {
        deviate not-supported;
    }

    deviation /oc-intf:interfaces/oc-intf:interface/oc-vlan:routed-vlan/oc-ip:ipv6/oc-ip:addresses/oc-ip:address/oc-ip:vrrp/oc-ip:vrrp-group/oc-ip:config/oc-ip:preempt-delay {
        deviate not-supported;
    }

    deviation /oc-intf:interfaces/oc-intf:interface/oc-vlan:routed-vlan/oc-ip:ipv6/oc-ip:addresses/oc-ip:address/oc-ip:vrrp/oc-ip:vrrp-group/oc-ip:config/oc-ip:accept-mode {
        deviate not-supported;
    }

    deviation /oc-intf:interfaces/oc-intf:interface/oc-vlan:routed-vlan/oc-ip:ipv6/oc-ip:addresses/oc-ip:address/oc-ip:vrrp/oc-ip:vrrp-group/oc-ip:state/oc-ip:preempt-delay {
        deviate not-supported;
    }

    deviation /oc-intf:interfaces/oc-intf:interface/oc-vlan:routed-vlan/oc-ip:ipv6/oc-ip:addresses/oc-ip:address/oc-ip:vrrp/oc-ip:vrrp-group/oc-ip:state/oc-ip:accept-mode {
        deviate not-supported;
    }

    deviation /oc-intf:interfaces/oc-intf:interface/oc-vlan:routed-vlan/oc-ip:ipv4/oc-ip:addresses/oc-ip:address/oc-ip:vrrp/oc-ip:vrrp-group/oc-ip:interface-tracking {
        deviate not-supported;
    }

    deviation /oc-intf:interfaces/oc-intf:interface/oc-vlan:routed-vlan/oc-ip:ipv6/oc-ip:addresses/oc-ip:address/oc-ip:vrrp/oc-ip:vrrp-group/oc-ip:interface-tracking {
        deviate not-supported;
    }

    deviation /oc-intf:interfaces/oc-intf:interface/oc-vlan:routed-vlan/oc-ip:ipv6/oc-ip:addresses/oc-ip:address/oc-ip:vrrp/oc-ip:vrrp-group/oc-ip:config/oc-ip:virtual-link-local {
        deviate not-supported;
    }

    deviation /oc-intf:interfaces/oc-intf:interface/oc-vlan:routed-vlan/oc-ip:ipv6/oc-ip:addresses/oc-ip:address/oc-ip:vrrp/oc-ip:vrrp-group/oc-ip:state/oc-ip:virtual-link-local {
        deviate not-supported;
    }
    deviation /oc-intf:interfaces/oc-intf:interface/oc-vlan:routed-vlan/oc-ip:ipv6/oc-ip:config/oc-ip:dup-addr-detect-transmits {
        deviate not-supported;
    }
    deviation /oc-intf:interfaces/oc-intf:interface/oc-vlan:routed-vlan/oc-ip:ipv6/oc-ip:state/oc-ip:dup-addr-detect-transmits {
        deviate not-supported;
    }  

    deviation /oc-intf:interfaces/oc-intf:interface/oc-intf:subinterfaces/oc-intf:subinterface/oc-ip:ipv6/oc-ip:unnumbered {
        deviate not-supported;
    }
    deviation /oc-intf:interfaces/oc-intf:interface/oc-intf:subinterfaces/oc-intf:subinterface/oc-ip:ipv6/oc-ip-ext:autoconf {
        deviate not-supported;
    }

    deviation /oc-intf:interfaces/oc-intf:interface/oc-tun:tunnel {
        deviate not-supported;
    }

    deviation /oc-intf:interfaces/oc-intf:interface/oc-intf:subinterfaces/oc-intf:subinterface/oc-ip:ipv6/oc-ip:neighbors/oc-ip:neighbor/oc-ip:state/oc-ip:is-router {
      deviate not-supported;
    }

    deviation /oc-intf:interfaces/oc-intf:interface/oc-intf:subinterfaces/oc-intf:subinterface/oc-ip:ipv6/oc-ip:neighbors/oc-ip:neighbor/oc-ip:state/oc-ip:neighbor-state {
      deviate not-supported;
    }
    deviation /oc-intf:interfaces/oc-intf:interface/oc-intf:state/oc-intf:logical {
        deviate not-supported;
    }

    deviation /oc-intf:interfaces/oc-intf:interface/oc-eth:ethernet/oc-vlan:switched-vlan/oc-vlan:config/oc-vlan:native-vlan {
        deviate not-supported;
    }

    deviation /oc-intf:interfaces/oc-intf:interface/oc-eth:ethernet/oc-eth:state/oc-eth:mac-address {
        deviate not-supported;
    }

    deviation /oc-intf:interfaces/oc-intf:interface/oc-eth:ethernet/oc-eth:config/oc-eth:enable-flow-control {
        deviate not-supported;
    }

    deviation /oc-intf:interfaces/oc-intf:interface/oc-eth:ethernet/oc-eth:state/oc-eth:enable-flow-control {
        deviate not-supported;
    }

    deviation /oc-intf:interfaces/oc-intf:interface/oc-eth:ethernet/oc-eth:state/oc-eth:hw-mac-address {
        deviate not-supported;
    }

    /*deviation /oc-intf:interfaces/oc-intf:interface/oc-intf:subinterfaces/oc-intf:subinterface/oc-ip:ipv6/oc-ip:router-advertisement/oc-ip:config/oc-ip:suppress {
        deviate replace {
            default true;
        }
    }
    deviation /oc-intf:interfaces/oc-intf:interface/oc-intf:subinterfaces/oc-intf:subinterface/oc-ip:ipv6/oc-ip:router-advertisement/oc-ip:state/oc-ip:suppress {
        deviate replace {
            default true;
        }
    }
    deviation /oc-intf:interfaces/oc-intf:interface/oc-vlan:routed-vlan/oc-ip:ipv6/oc-ip:router-advertisement/oc-ip:config/oc-ip:suppress {
        deviate replace {
            default true;
        }
    }
    deviation /oc-intf:interfaces/oc-intf:interface/oc-vlan:routed-vlan/oc-ip:ipv6/oc-ip:router-advertisement/oc-ip:state/oc-ip:suppress {
        deviate replace {
            default true;
        }
    }*/
    deviation "/oc-intf:interfaces/oc-intf:interface/oc-intf:subinterfaces/oc-intf:subinterface/oc-ip:ipv4/oc-ip:state/oc-ip:counters/in-bits-per-second" {
        deviate not-supported;
    }
    deviation "/oc-intf:interfaces/oc-intf:interface/oc-intf:subinterfaces/oc-intf:subinterface/oc-ip:ipv6/oc-ip:state/oc-ip:counters/in-bits-per-second" {
        deviate not-supported;
    }
    deviation "/oc-intf:interfaces/oc-intf:interface/oc-vlan:routed-vlan/oc-ip:ipv4/oc-ip:state/oc-ip:counters/in-bits-per-second" {
        deviate not-supported;
    }
    deviation "/oc-intf:interfaces/oc-intf:interface/oc-vlan:routed-vlan/oc-ip:ipv6/oc-ip:state/oc-ip:counters/in-bits-per-second" {
        deviate not-supported;
    }
    deviation "/oc-intf:interfaces/oc-intf:interface/oc-intf:subinterfaces/oc-intf:subinterface/oc-ip:ipv4/oc-ip:state/oc-ip:counters/out-bits-per-second" {
        deviate not-supported;
    }
    deviation "/oc-intf:interfaces/oc-intf:interface/oc-intf:subinterfaces/oc-intf:subinterface/oc-ip:ipv6/oc-ip:state/oc-ip:counters/out-bits-per-second" {
        deviate not-supported;
    }
    deviation "/oc-intf:interfaces/oc-intf:interface/oc-vlan:routed-vlan/oc-ip:ipv4/oc-ip:state/oc-ip:counters/out-bits-per-second" {
        deviate not-supported;
    }
    deviation "/oc-intf:interfaces/oc-intf:interface/oc-vlan:routed-vlan/oc-ip:ipv6/oc-ip:state/oc-ip:counters/out-bits-per-second" {
        deviate not-supported;
    }
    deviation "/oc-intf:interfaces/oc-intf:interface/oc-intf:subinterfaces/oc-intf:subinterface/oc-ip:ipv4/oc-ip:state/oc-ip:counters/in-utilization" {
        deviate not-supported;
    }
    deviation "/oc-intf:interfaces/oc-intf:interface/oc-intf:subinterfaces/oc-intf:subinterface/oc-ip:ipv6/oc-ip:state/oc-ip:counters/in-utilization" {
        deviate not-supported;
    }
    deviation "/oc-intf:interfaces/oc-intf:interface/oc-vlan:routed-vlan/oc-ip:ipv4/oc-ip:state/oc-ip:counters/in-utilization" {
        deviate not-supported;
    }
    deviation "/oc-intf:interfaces/oc-intf:interface/oc-vlan:routed-vlan/oc-ip:ipv6/oc-ip:state/oc-ip:counters/in-utilization" {
        deviate not-supported;
    }
    deviation "/oc-intf:interfaces/oc-intf:interface/oc-intf:subinterfaces/oc-intf:subinterface/oc-ip:ipv4/oc-ip:state/oc-ip:counters/out-utilization" {
        deviate not-supported;
    }
    deviation "/oc-intf:interfaces/oc-intf:interface/oc-intf:subinterfaces/oc-intf:subinterface/oc-ip:ipv6/oc-ip:state/oc-ip:counters/out-utilization" {
        deviate not-supported;
    }
    deviation "/oc-intf:interfaces/oc-intf:interface/oc-vlan:routed-vlan/oc-ip:ipv4/oc-ip:state/oc-ip:counters/out-utilization" {
        deviate not-supported;
    }
    deviation "/oc-intf:interfaces/oc-intf:interface/oc-vlan:routed-vlan/oc-ip:ipv6/oc-ip:state/oc-ip:counters/out-utilization" {
        deviate not-supported;
    }
}
