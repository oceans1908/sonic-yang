module openconfig-pms-ext {

  yang-version "1";

  // namespace
  namespace "http://openconfig.net/yang/pms/extension";

  prefix "oc-pms-ext";

  import openconfig-interfaces { prefix oc-if; }
  import ietf-yang-types { prefix yang; }
  import openconfig-extensions { prefix oc-ext; }
  import openconfig-pms-types { prefix oc-pms-types; }


  organization
      "SONiC";

  contact
      "SONiC";

  description
    "This module defines configuration and operational state data
    for the Port Mac Security protocol.";

  oc-ext:openconfig-version "0.1.0";

  revision "2024-08-15" {
    description
      "Added support for sticky-mac feature";
    reference "0.1.1";
  }

  revision "2021-05-10" {
    description
      "Initial public revision";
    reference "0.1.0";
  }

  // OpenConfig specific extensions for module metadata.
  oc-ext:regexp-posix;
  oc-ext:catalog-organization "openconfig";
  oc-ext:origin "openconfig";

  // identity statements


  // grouping statements

  grouping pms-ext-interface-config {
    description
      "Configuration data for PMS on each interface";

    leaf name {
      type oc-if:base-interface-ref;
      description
        "Reference to the PMS Ethernet interface";
    }

    leaf admin-enable {
        type boolean;
        default false;
        description
            "Enable/Disable PMS";
    }

    leaf maximum {
        type uint16 {
            range "1..4097" {
                error-message "Invalid value.";
            }
        }
        default 1;
        description
            "Set the maximum number of allowed MAC addresses on a port";
    }

    leaf violation {
        type identityref {
            base oc-pms-types:PMS_VIOLATION_ACTION;
        }
        default oc-pms-types:PROTECT;
        description
            "PMS violation action";
    }

    leaf sticky-mac {
        type boolean;
        default false;
        description
            "Enable/Disable sticky-mac feature";
    }

  }


  grouping pms-ext-interface-state {
    description
      "Operational state data for PMS on each interface";

    container oper-info {
        description
            "Operational info";
        leaf fdb-count {
            type uint16;
            default 0;
            description
                "total no of MAC address learnt on this port";
        }

        leaf violation-count {
            type uint32;
            default 0;
            description
                "No of times violation has been hit on this port";
        }

        leaf err-disabled {
            type boolean;
            default false;
            description
                "Error disabled status of the port";
        }
    }
  }



  grouping pms-ext-interface-top {
    description
      "Top-level grouping ";

    container interfaces {
      description
        "Enclosing container ";

      list interface {
        key "name";
        description
          "List of interfaces on which PMS is enabled / available";

        leaf name {
          type leafref {
            path "../config/name";
          }
          description
            "Reference to the PMS Ethernet interface";
        }

        container config {
          description
            "Configuration data for PMS on each interface";

          uses pms-ext-interface-config;
        }

        container state {

            config false;

            description
                "Operational state data ";

            uses pms-ext-interface-config;
            uses pms-ext-interface-state;
        }

      }
    }
  }



  grouping pms-ext-top {
    description
      "Top-level grouping for PMS model";

    container port-security {
      description
        "Top-level container for PMS configuration and state data";

      uses pms-ext-interface-top;
    }
  }

  // data definition statements

  uses pms-ext-top;

}
