module openconfig-lldp-annot {

    yang-version "1.1";

    namespace "http://openconfig.net/yang/lldp-annot";
    prefix "oc-lldp-annot";

    import sonic-extensions { prefix sonic-ext; }
    import openconfig-lldp { prefix oc-lldp; }
    import openconfig-lldp-ext { prefix oc-lldp-ext; }

    // meta
    organization
       "SONiC";

    contact
       "SONiC";

    description
       "SONIC LLDP";

    revision 2024-03-05 {
      description
		"1. Changed lldp state globals to refer APPL_DB";
      reference "0.1.1";
    }

    revision 2020-04-16 {
       description
          "Initial revision.";
    }

	deviation /oc-lldp:lldp {
		deviate add {
                        sonic-ext:user-role-priv "write:netadmin";
		}
    }
	
	deviation /oc-lldp:lldp/oc-lldp:config {
		deviate add {
			sonic-ext:table-name "LLDP";
			sonic-ext:key-transformer "lldp_global_key_xfmr";
		}
    }

	deviation /oc-lldp:lldp/oc-lldp:config/oc-lldp:hello-timer {
		deviate add {
			sonic-ext:field-name "hello_time";
		}
	}

	deviation /oc-lldp:lldp/oc-lldp:config/oc-lldp:system-name {
		deviate add {
			sonic-ext:field-name "system_name";
		}
	}

	deviation /oc-lldp:lldp/oc-lldp:config/oc-lldp:system-description {
		deviate add {
			sonic-ext:field-name "system_description";
		}
	}

	deviation /oc-lldp:lldp/oc-lldp:config/oc-lldp:suppress-tlv-advertisement {
		deviate add {
            sonic-ext:composite-field-names "LLDP:supp_mgmt_address_tlv, LLDP:supp_system_capabilities_tlv";
            sonic-ext:subscribe-delete-as-update "true";
			sonic-ext:field-transformer "suppress_tlv_adv_xfmr";
		}
	}

	deviation /oc-lldp:lldp/oc-lldp:state {
		deviate add {
			sonic-ext:db-name "APPL_DB";
			sonic-ext:table-name "LLDP_GLOBALS";
			sonic-ext:key-transformer "lldp_global_key_xfmr";
		}
    }

	deviation /oc-lldp:lldp/oc-lldp:state/oc-lldp:hello-timer {
		deviate add {
			sonic-ext:field-name "hello_time";
		}
	}

	deviation /oc-lldp:lldp/oc-lldp:state/oc-lldp:system-name {
		deviate add {
			sonic-ext:field-name "system_name";
		}
	}

	deviation /oc-lldp:lldp/oc-lldp:state/oc-lldp:system-description {
		deviate add {
			sonic-ext:field-name "system_description";
		}
	}

	deviation /oc-lldp:lldp/oc-lldp:state/oc-lldp:suppress-tlv-advertisement {
		deviate add {
            sonic-ext:composite-field-names "LLDP_GLOBALS:supp_mgmt_address_tlv, LLDP_GLOBALS:supp_system_capabilities_tlv";
            sonic-ext:subscribe-delete-as-update "true";
			sonic-ext:field-transformer "suppress_tlv_adv_xfmr";
		}
	}

	deviation /oc-lldp:lldp/oc-lldp:interfaces/oc-lldp:interface {
		deviate add {
			sonic-ext:subtree-transformer "lldp_intf_xfmr";
			sonic-ext:path-transformer "lldp_intf_path_xfmr";
		}
	}
	deviation /oc-lldp:lldp/oc-lldp:interfaces/oc-lldp:interface/oc-lldp:neighbors/oc-lldp:neighbor/oc-lldp:state/oc-lldp:age {
		deviate add {
			sonic-ext:subscribe-on-change "disable";
		}
	}

	deviation /oc-lldp:lldp/oc-lldp:interfaces/oc-lldp:interface/oc-lldp:neighbors/oc-lldp:neighbor/oc-lldp:state/oc-lldp:last-update {
		deviate add {
			sonic-ext:subscribe-on-change "disable";
		}
	}
	deviation /oc-lldp:lldp/oc-lldp:interfaces/oc-lldp:interface/oc-lldp:neighbors/oc-lldp:neighbor/oc-lldp:state/oc-lldp:management-address-type {
		deviate add {
			sonic-ext:field-name "lldp_rem_man_addr_type";
			sonic-ext:field-transformer "man_addr_type_fld_xfmr";
		}
	}
}
