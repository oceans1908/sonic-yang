module ietf-ptp-ext {

	yang-version 1.1;

	// namespace
	namespace "urn:ietf:params:xml:ns:yang:ietf-ptp-ext";

	prefix ptp-ext;

	import ietf-ptp {prefix ptp; }
	import openconfig-ptp-rpc {prefix oc-ptp-rpc; }
	import openconfig-interfaces { prefix "oc-if"; }
	// meta
	organization "Broadcom";

	contact "Broadcom";

	description
		"Copyright (c) 2020 IETF Trust and the persons identified as
		authors of the code.  All rights reserved.

		Redistribution and use in source and binary forms, with or
		without modification, is permitted pursuant to, and subject to
		the license terms contained in, the Simplified BSD License set
		forth in Section 4.c of the IETF Trust's Legal Provisions
		Relating to IETF Documents
		(https://trustee.ietf.org/license-info).

		This version of this YANG module is part of RFC XXXX
		(https://www.rfc-editor.org/info/rfcXXXX); see the RFC itself
		for full legal notices.";

	revision 2024-06-17 {
		description
			"Added Support for source-interface command for IPV4 and IPV6
				multicast,Servo state,role,local-priority and debug enablement";
		reference "0.0.2";
	}

	revision 2019-12-29 {
		description
			"Initial extension file.";
		reference "0.0.1";
	}

	typedef ptp-clock-type {
		type enumeration {
			enum BC {
				value 1;
				description
					"boundary clock";
			}
			enum P2P_TC {
				value 2;
				description
					"peer-to-peer transparent clock";
			}
			enum E2E_TC {
				value 3;
				description
					"end-to-end transparent clock";
			}
			enum disable {
				value 4;
				description
					"disabled";
			}
		}
		description
			"Type definition for options when setting the clock-type
			attribute in the default data set";
	}

	typedef ptp-network-transport {
		type enumeration {
			enum L2 {
				value 1;
				description
					"Layer 2 network";
			}
			enum UDPv4 {
				value 2;
				description
					"UDPv4 network";
			}
			enum UDPv6 {
				value 3;
				description
					"UDPv2 network";
			}
		}
		description
			"Type definition for options when setting the network transport
			attribute in the default data set";
	}

	typedef ptp-unicast-multicast {
		type enumeration {
			enum unicast {
				value 1;
				description
					"unicast";
			}
			enum multicast {
				value 2;
				description
					"multicast";
			}
		}
		description
			"Type definition for options when setting the unicast-multicast 
			attribute in the default data set";
	}

	typedef ptp-domain-profile {
		type enumeration {
			enum ieee1588 {
				value 1;
				description
					"default profile";
			}
			enum g8275.1 {
				value 2;
				description
					"g8275.1 profile";
			}
			enum g8275.2 {
				value 3;
				description
					"g8275.2 profile";
			}
		}
		description
			"Type definition for options when setting the domain-profile
			attribute in the default data set";
	}

	typedef ptp-servo-state {
		type enumeration {
			enum "acquiring-lock" {
				value 1;
				description
					"Acquiring lock state";
			}
			enum "locked" {
				value 2;
				description
					"Locked state";
			}
			enum "holdover" {
				value 3;
				description
					"Holdover state";
			}
			enum "ref-failed" {
				value 4;
				description
					"Ref Failed state";
			}
			enum "no-active-server" {
				value 5;
				description
					"No Active Server State";
			}
			enum "unknown" {
				value 6;
				description
					"unknown state";
			}
		}
		description
			"Type definition for ptp servo state when displaying the ptp servo
			details";
	}

	typedef ptp-servo-lock-status {
		type enumeration {
			enum "phase-locked" {
				value 1;
				description
					"Phase locked lock-status";
			}
			enum "freq-locked" {
				value 2;
				description
					"Frequency locked lock-status";
			}
			enum "unknown" {
				value 3;
				description
					"Unknown lock-status";
			}
		}
		description
			"Type definition for ptp servo lock status when displaying the ptp servo
			details";
	}

        typedef ptp-interface-role {
                type enumeration {
                        enum "DYNAMIC" {
                                value 1;
                                description
                                        "Enable dynamic role on the interface.";
                        }
                        enum "MASTER" {
                                value 2;
                                description
                                        "Enable master only role on the interface.";
                        }
                        enum "SLAVE" {
                                value 3;
                                description
                                        "Enable slave only role on the interface.";
                        }
                }
		description
			"Type definition for ptp interface role configuration";
        }

	grouping servo-status {
		description 
			"The servo data set of the clock";
		container servo-status-info {
		    config false;
			description
				"The servo data set of the clock";

			leaf servo-state {
			type ptp-servo-state;
			description
				"Servo state";
			}
			leaf lock-status {
				type ptp-servo-lock-status;
				description 
					"Servo locked status";
			}
		}
	} 
	// augment statements
	augment "/ptp:ptp/ptp:instance-list/ptp:default-ds" {
		description "default data set";
		leaf log-announce-interval {
			type int8;
			description
				"The base-2 logarithm of the mean
				announceInterval (mean time interval between
						successive Announce messages).";
		}
		leaf announce-receipt-timeout {
			type uint8 {
				range "2..255" {
					error-message "Invalid value passed for announce-receipt-timeout";
				}
			}
			description
				"The number of announceIntervals that have to pass
				without receipt of an Announce message before the
				occurrence of the event ANNOUNCE_RECEIPT_TIMEOUT_
				EXPIRES.";
		}
		leaf log-sync-interval {
			type int8;
			description
				"The base-2 logarithm of the mean SyncInterval
				for multicast messages.  The rates for unicast
				transmissions are negotiated separately on a per-port
				basis and are not constrained by this attribute.";
		}
		leaf log-min-delay-req-interval {
			type int8;
			description
				"The base-2 logarithm of the minDelayReqInterval
				(the minimum permitted mean time interval between
				 successive Delay_Req messages).";
		}
		leaf clock-type {
			type string {
				pattern "(BC)|(P2P_TC)|(E2E_TC)|(disable)" {
					error-message "Invalid value passed for clock-type";
				}
			}
			description
				"Defines the role of the default-data-set";
		}
		leaf network-transport {
			type string {
				pattern "(L2)|(UDPv4)|(UDPv6)" {
					error-message "Invalid value passed for network-transport";
				}
			}
			description
				"The network transport used for communication";
		}
		leaf unicast-multicast {
			type string {
				pattern "(unicast)|(multicast)" {
					error-message "Invalid value passed for unicast-multicast";
				}
			}
			description
				"Whether the network transport uses unicast or
				multicast communication";
		}
		leaf domain-profile {
			type string {
				pattern "(ieee1588)|(G.8275.1)|(G.8275.2)" {
					error-message "Invalid value passed for domain-profile";
				}
			}
			description
				"the method to be used when comparing data sets during
				the Best Master Clock Algorithm.";
		}
		leaf udp6-scope {
			type uint8;
			description
				"the desired scope for the IPv6 multicast messages.
				This will be used as the second byte of the primary 
				address. This option is only relevant with IPv6
				transport. See RFC 4291. The default is 14 (0x0E) for
				the global scope.";
		}
		leaf source-interface {
			type leafref {
				path "/oc-if:interfaces/oc-if:interface/oc-if:name";
			}
			description
				"Source interface whose IP to use as source ip for PTP IPv4
				 and IPv6 multicast transport mode.";
		}
	}

	augment "/ptp:ptp/ptp:instance-list/ptp:port-ds-list" {
		description "port data set list";
		leaf-list unicast-table {
			type string;
			must "((not(../role)) or (../role != 'MASTER'))" {
				error-message "PTP role and master table conflict";
			}
			description
				"The comma-separated list of ip addresses to use for
				master";
		}
		leaf role {
			type ptp-interface-role;
			must "( ((current() = 'MASTER') and (not(../unicast-table))) or ((current() != 'MASTER')))" {
				error-message "PTP role and master table conflict";
			}
			default "DYNAMIC";
			description
				"Configure the role of interface.";
		}
		leaf local-priority {
			type uint8 {
				range "1..255";
			}
			default 128;
			description
				"Configure the local-priority attribute used for the profile G8275-1 and G8275-2.";
		}
	}
	deviation "/ptp:ptp/ptp:instance-list/ptp:default-ds/ptp:domain-number" {
		deviate replace {
			type uint8 {
				range "0..127" {
					error-message "Invalid value passed for domain-number";
				}
			}
		}
	}
	deviation "/ptp:ptp/ptp:transparent-clock-default-ds" {
		deviate not-supported;
	}
	deviation "/ptp:ptp/ptp:transparent-clock-port-ds-list" {
		deviate not-supported;
	}
	augment "/ptp:ptp/ptp:instance-list" {
		description "Adds extensions to PTP instance";
		uses servo-status;
	}
	augment "/ptp:ptp/ptp:instance-list" {
		description "Ptp Debug info";
		container ptp-debug {
			description "Container for ptp debug info";
			list ptp-debug-info {
				key "debug-option";
				config false;
				description
					"Contains detail of the global debug information configured for PTP.";
				leaf debug-option {
					type oc-ptp-rpc:ptp-debug-option;
					description
						"Contains debug options enabled for PTP";
				}
				leaf debug-level {
					type uint8 {
						range "1..5";
					}
					description
						"Debug level of the debug option.";
				}
			}
		}
	}
}
