module sonic-flow-based-services {
    namespace "http://github.com/Azure/sonic-flow-based-services";
    prefix sfbs;
    yang-version 1.1;

    import ietf-inet-types {
        prefix inet;
    }

    import sonic-extension {
        prefix sonic-ext;
    }

    import sonic-port {
        prefix sprt;
    }

    import sonic-portchannel {
        prefix spc;
    }

    import sonic-vlan {
        prefix svlan;
    }

    import sonic-mirror-session {
        prefix sms;
    }

    import sonic-interface {
        prefix sint;
    }

    organization
        "SONiC";

    contact
        "SONiC";

    description
        "SONIC Flow Based Services";

    revision 2020-02-26 {
        description
            "Initial revision.";
    }

    typedef classifier-match-type {
        type enumeration {
            enum FIELDS;
            enum ACL;
        }
    }

    typedef policy-types {
        type enumeration {
            enum QOS;
            enum MONITORING;
            enum FORWARDING;
            enum ACL_COPP;
        }
    }

    typedef policy-binding-stages {
        type enumeration {
            enum INGRESS;
            enum EGRESS;
        }
    }

    typedef pbf-next-hop-group-type {
        type enumeration {
            enum IPV4;
            enum IPV6;
        }
    }

    typedef pbf-replication-group-type {
        type enumeration {
            enum IPV4;
            enum IPV6;
        }
    }

    typedef packet-color-types {
        type enumeration {
            enum GREEN;
            enum YELLOW;
            enum RED;
        }
    }

    grouping classifier-attributes {
        leaf DESCRIPTION {
            type string {
                length 1..256 {
                    error-app-tag policy-description-invalid-length;
                }
            }
        }

        leaf MATCH_TYPE {
            type classifier-match-type;
            mandatory true;
            sonic-ext:custom-validation ValidateLeafConstant;
        }

        leaf ACL_NAME {
            type string {
                pattern '[a-zA-Z0-9]{1}([-a-zA-Z0-9_]{0,71})';
                length 1..72;
            }
            when "current()/../MATCH_TYPE = 'ACL'";
            must "current()/../ACL_TYPE != ''" {
                error-app-tag acl-type-missing;
                error-message "ACL type is not specified";
            }
        }

        leaf ACL_TYPE {
            type enumeration {
                enum L2;
                enum L3;
                enum L3V6;
            }
            when "current()/../MATCH_TYPE = 'ACL'";
            must "current()/../ACL_NAME != ''" {
                error-app-tag acl-name-missing;
                error-message "ACL name is not specified";
            }
        }

        leaf ETHER_TYPE {
            type string {
                pattern "0[xX][6-9a-fA-F][0-9a-fA-F]{2,3}|0[xX][1-9a-fA-F][0-9a-fA-F]{3,4}" {
                    error-message "Invalid Ether Type";
                    error-app-tag ether-type-invalid;
                }
            }
            when "current()/../MATCH_TYPE = 'FIELDS'";
        }

        leaf SRC_MAC {
            type string {
                pattern "[0-9a-fA-F]{2}(:[0-9a-fA-F]{2}){5}|[0-9a-fA-F]{2}(:[0-9a-fA-F]{2}){5}/[0-9a-fA-F]{2}(:[0-9a-fA-F]{2}){5}";
            }
            when "current()/../MATCH_TYPE = 'FIELDS'";
        }

        leaf DST_MAC {
            type string {
                pattern "[0-9a-fA-F]{2}(:[0-9a-fA-F]{2}){5}|[0-9a-fA-F]{2}(:[0-9a-fA-F]{2}){5}/[0-9a-fA-F]{2}(:[0-9a-fA-F]{2}){5}";
            }
            when "current()/../MATCH_TYPE = 'FIELDS'";
        }

        leaf VLAN {
            type uint16 {
                range "1..4094" {
                    error-app-tag vlanid-invalid;
                    error-message "Vlan ID out of range";
                }
            }
            when "current()/../MATCH_TYPE = 'FIELDS'";
        }

        leaf PCP {
            type uint8 {
                range "0..7" {
                    error-app-tag invalid-pcp-value;
                    error-message "Invalid PCP Value.";
                }
            }
            when "current()/../MATCH_TYPE = 'FIELDS'";
        }

        leaf DEI {
            type uint8 {
                range "0..1" {
                    error-app-tag invalid-dei-value;
                    error-message "Invalid DEI Value.";
                }
            }
            when "current()/../MATCH_TYPE = 'FIELDS'";
        }

        leaf IP_PROTOCOL {
            type uint8;
            when "current()/../MATCH_TYPE = 'FIELDS'";
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "IP Protocol can be configured only when Ethertype is IPv4 or IPv6";
            }
        }

        leaf SRC_IP {
            type inet:ipv4-prefix;
            when "current()/../MATCH_TYPE = 'FIELDS'";
            must "(not(current()/../SRC_IPV6)) and (not(current()/../DST_IPV6))" {
                error-message "Configuring IPv4 and IPv6 header fields in the same classifier is not allowed.";
            }
            must "(translate(current()/../ETHER_TYPE, 'ABCDEFX', 'abcdefx') = '0x800') or (not(current()/../ETHER_TYPE))" {
                error-app-tag src-ip-ethertype-not-ipv4;
                error-message "Source IP address can be configured only when ethertype is IPv4";
            }
        }

        leaf DST_IP {
            type inet:ipv4-prefix;
            when "current()/../MATCH_TYPE = 'FIELDS'";
            must "(not(current()/../SRC_IPV6)) and (not(current()/../DST_IPV6))" {
                error-message "Configuring IPv4 and IPv6 header fields in the same classifier is not allowed.";
            }
            must "(translate(current()/../ETHER_TYPE, 'ABCDEFX', 'abcdefx') = '0x800') or (not(current()/../ETHER_TYPE))" {
                error-app-tag dst-ip-ethertype-not-ipv4;
                error-message "Destination IP address can be configured only when ethertype is IPv4";
            }
        }

        leaf SRC_IPV6 {
            type inet:ipv6-prefix;
            when "current()/../MATCH_TYPE = 'FIELDS'";
            must "(not(current()/../SRC_IP)) and (not(current()/../DST_IP))" {
                error-message "Configuring IPv4 and IPv6 header fields in the same classifier is not allowed.";
            }
            must "(translate(current()/../ETHER_TYPE, 'ABCDEFX', 'abcdefx') = '0x86dd') or (not(current()/../ETHER_TYPE))" {
                error-app-tag src-ip-ethertype-not-ipv6;
                error-message "Source IPv6 address can be configured only when ethertype is IPv6";
            }
        }

        leaf DST_IPV6 {
            type inet:ipv6-prefix;
            when "current()/../MATCH_TYPE = 'FIELDS'";
            must "(not(current()/../SRC_IP)) and (not(current()/../DST_IP))" {
                error-message "Configuring IPv4 and IPv6 header fields in the same classifier is not allowed.";
            }
            must "(translate(current()/../ETHER_TYPE, 'ABCDEFX', 'abcdefx') = '0x86dd') or (not(current()/../ETHER_TYPE))" {
                error-app-tag dst-ip-ethertype-not-ipv6;
                error-message "Destination IPv6 address can be configured only when ethertype is IPv6";
            }
        }

        leaf DSCP {
            type uint8 {
                range "0..63" {
                    error-app-tag invalid-dscp-value;
                    error-message "Invalid DSCP Value.";
                }
            }
            when "current()/../MATCH_TYPE = 'FIELDS'";
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "IP Protocol can be configured only when Ethertype is IPv4 or IPv6";
            }
        }

        leaf ECN {
            type uint8 {
                range "0..3" {
                    error-app-tag invalid-ecn-value;
                    error-message "Invalid ECN Value.";
                }
            }
            sonic-ext:custom-validation ValidateLeafNotSupported;
            when "current()/../MATCH_TYPE = 'FIELDS'";
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "IP Protocol can be configured only when Ethertype is IPv4 or IPv6";
            }
        }

        leaf L4_SRC_PORT {
            type uint16;
            when "current()/../MATCH_TYPE = 'FIELDS'";
            must "((current()/../IP_PROTOCOL = 6) or (current()/../IP_PROTOCOL = 17))" {
                error-app-tag ip-protocol-not-tcp-or-udp;
                error-message "Layer 4 source port can be configured only when IP protocol is TCP or UDP";
            }
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "TCP/UDP ports can be configured only when Ethertype is IPv4 or IPv6";
            }
            must "not(current()/../L4_SRC_PORT_RANGE)" {
                error-message "Source port and source port range can not be configured at the same time";
            }
        }

        leaf L4_SRC_PORT_RANGE {
            type string {
                pattern "([0-9]{1,4}|[1-5][0-9]{4}|6[0-4][0-9]{3}|65[0-4][0-9]{2}|655[0-2][0-9]|6553[0-5])(-)([0-9]{1,4}|[1-5][0-9]{4}|6[0-4][0-9]{3}|65[0-4][0-9]{2}|655[0-2][0-9]|6553[0-5])";
            }
            when "current()/../MATCH_TYPE = 'FIELDS'";
            must "((current()/../IP_PROTOCOL = 6) or (current()/../IP_PROTOCOL = 17))" {
                error-app-tag ip-protocol-not-tcp-or-udp;
                error-message "Layer 4 source port can be configured only when IP protocol is TCP or UDP";
            }
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "TCP/UDP ports can be configured only when Ethertype is IPv4 or IPv6";
            }
            must "not(current()/../L4_SRC_PORT)" {
                error-message "Source port and source port range can not be configured at the same time";
            }
        }

        leaf L4_DST_PORT {
            type uint16;
            when "current()/../MATCH_TYPE = 'FIELDS'";
            must "((current()/../IP_PROTOCOL = 6) or (current()/../IP_PROTOCOL = 17))" {
                error-app-tag ip-protocol-not-tcp-or-udp;
                error-message "Layer 4 source port can be configured only when IP protocol is TCP or UDP";
            }
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "TCP/UDP ports can be configured only when Ethertype is IPv4 or IPv6";
            }
            must "not(current()/../L4_DST_PORT_RANGE)" {
                error-message "Destination port and destination port range can not be configured at the same time";
            }
        }

        leaf L4_DST_PORT_RANGE {
            type string {
                pattern "([0-9]{1,4}|[1-5][0-9]{4}|6[0-4][0-9]{3}|65[0-4][0-9]{2}|655[0-2][0-9]|6553[0-5])(-)([0-9]{1,4}|[1-5][0-9]{4}|6[0-4][0-9]{3}|65[0-4][0-9]{2}|655[0-2][0-9]|6553[0-5])";
            }
            when "current()/../MATCH_TYPE = 'FIELDS'";
            must "((current()/../IP_PROTOCOL = 6) or (current()/../IP_PROTOCOL = 17))" {
                error-app-tag ip-protocol-not-tcp-or-udp;
                error-message "Layer 4 source port can be configured only when IP protocol is TCP or UDP";
            }
            must "((translate(current()/../ETHER_TYPE, 'ABCDEFX', 'abcdefx') = '0x800') or ((translate(current()/../ETHER_TYPE, 'ABCDEFX', 'abcdefx') = '0x86dd')) or (not(current()/../ETHER_TYPE)))" {
                error-app-tag ethertype-not-ipv4-ipv6;
                error-message "TCP/UDP ports can be configured only when Ethertype is IPv4 or IPv6";
            }
            must "not(current()/../L4_DST_PORT)" {
                error-message "Destination port and destination port range can not be configured at the same time";
            }
        }

        leaf TCP_FLAGS {
            when "current()/../MATCH_TYPE = 'FIELDS'";
            must "current()/../IP_PROTOCOL = 6" {
                error-app-tag ip-protocol-not-tcp;
                error-message "TCP Flags can be configured only when IP protocol is IP protocol is TCP";
            }

            type string {
                pattern "(0[xX][1-9a-fA-F][0-9a-fA-F]?|[1-9][0-9]?|1[0-9]{2}|2[0-5]{2})/(0[xX][1-9a-fA-F][0-9a-fA-F]?|[1-9][0-9]?|1[0-9]{2}|2[0-5]{2})";
            }
        }
        leaf ICMP_TYPE {
            when "current()/../MATCH_TYPE = 'FIELDS'";
            type uint8;
            must "((current()/../IP_PROTOCOL = 1) or (current()/../IP_PROTOCOL = 58))" {
                error-app-tag ip-protocol-not-icmp-or-icmpv6;
                error-message "ICMP type can be configured only when IP protocol is ICMP or ICMPv6";
            }
        }

        leaf ICMP_CODE {
            when "current()/../MATCH_TYPE = 'FIELDS'";
            must "((current()/../IP_PROTOCOL = 1) or (current()/../IP_PROTOCOL = 58))" {
                error-app-tag ip-protocol-not-icmp-or-icmpv6;
                error-message "ICMP code can be configured only when IP protocol is ICMP or ICMPv6";
            }
            type uint8;
        }
    }

    grouping policy-section-attributes {
        leaf DESCRIPTION {
            type string {
                length 1..256 {
                    error-app-tag policy-description-invalid-length;
                }
            }
        }

        leaf PRIORITY {
            type uint16 {
                range "0..4095" {
                    error-app-tag invalid-priority;
                }
            }
            mandatory true;
            sonic-ext:custom-validation ValidateLeafConstant;
        }
    }

    grouping policy-section-qos-actions {
        leaf SET_DSCP {
            type uint8 {
                range "0..63" {
                    error-app-tag invalid-dscp-value;
                    error-message "Invalid DSCP value.";
                }
            }
            must "not(current()/../SET_MIRROR_SESSION)" {
                error-message "QoS and monitoring actions cant be configured at the same time.";
            }
            must "not(current()/../SET_INTERFACE)" {
                error-message "QoS and forwarding actions cant be configured at the same time.";
            }
            must "not(current()/../SET_IP_NEXTHOP)" {
                error-message "QoS and forwarding actions cant be configured at the same time.";
            }
            must "not(current()/../SET_IP_NEXTHOP_GROUP)" {
                error-message "QoS and forwarding actions cant be configured at the same time.";
            }
            must "not(current()/../SET_IP_REPLICATION_GROUP)" {
                error-message "QoS and forwarding actions cant be configured at the same time.";
            }
            must "not(current()/../SET_IPV6_NEXTHOP)" {
                error-message "QoS and forwarding actions cant be configured at the same time.";
            }
            must "not(current()/../SET_IPV6_NEXTHOP_GROUP)" {
                error-message "QoS and forwarding actions cant be configured at the same time.";
            }
            must "not(current()/../SET_IPV6_REPLICATION_GROUP)" {
                error-message "QoS and forwarding actions cant be configured at the same time.";
            }
            must "not(current()/../DEFAULT_PACKET_ACTION)" {
                error-message "QoS and forwarding actions cant be configured at the same time.";
            }
            must "not(current()/../SET_TRAP_QUEUE)" {
                error-message "QoS and CoPP actions cant be configured at the same time.";
            }
            when "/sonic-flow-based-services/POLICY_TABLE/POLICY_TABLE_LIST[POLICY_NAME=current()/../POLICY_NAME]/TYPE = 'QOS'";
        }

        leaf SET_ECN {
            type uint8 {
                range "0..3" {
                    error-app-tag invalid-ecn-value;
                    error-message "Invalid ECN value.";
                }
            }
            sonic-ext:custom-validation ValidateLeafNotSupported;
            must "not(current()/../SET_MIRROR_SESSION)" {
                error-message "QoS and monitoring actions cant be configured at the same time.";
            }
            must "not(current()/../SET_INTERFACE)" {
                error-message "QoS and forwarding actions cant be configured at the same time.";
            }
            must "not(current()/../SET_IP_NEXTHOP)" {
                error-message "QoS and forwarding actions cant be configured at the same time.";
            }
            must "not(current()/../SET_IP_NEXTHOP_GROUP)" {
                error-message "QoS and forwarding actions cant be configured at the same time.";
            }
            must "not(current()/../SET_IP_REPLICATION_GROUP)" {
                error-message "QoS and forwarding actions cant be configured at the same time.";
            }
            must "not(current()/../SET_IPV6_NEXTHOP)" {
                error-message "QoS and forwarding actions cant be configured at the same time.";
            }
            must "not(current()/../SET_IPV6_NEXTHOP_GROUP)" {
                error-message "QoS and forwarding actions cant be configured at the same time.";
            }
            must "not(current()/../SET_IPV6_REPLICATION_GROUP)" {
                error-message "QoS and forwarding actions cant be configured at the same time.";
            }
            must "not(current()/../DEFAULT_PACKET_ACTION)" {
                error-message "QoS and forwarding actions cant be configured at the same time.";
            }
            must "not(current()/../SET_TRAP_QUEUE)" {
                error-message "QoS and CoPP actions cant be configured at the same time.";
            }
            when "/sonic-flow-based-services/POLICY_TABLE/POLICY_TABLE_LIST[POLICY_NAME=current()/../POLICY_NAME]/TYPE = 'QOS'";
        }

        leaf SET_PACKET_COLOR {
            type packet-color-types;
            sonic-ext:custom-validation ValidateLeafNotSupported;
            must "not(current()/../SET_POLICER_CIR)" {
                error-message "Policer CIR and packet color actions cant be configured at the same time.";
            }
            must "not(current()/../SET_MIRROR_SESSION)" {
                error-message "QoS and monitoring actions cant be configured at the same time.";
            }
            must "not(current()/../SET_INTERFACE)" {
                error-message "QoS and forwarding actions cant be configured at the same time.";
            }
            must "not(current()/../SET_IP_NEXTHOP)" {
                error-message "QoS and forwarding actions cant be configured at the same time.";
            }
            must "not(current()/../SET_IP_NEXTHOP_GROUP)" {
                error-message "QoS and forwarding actions cant be configured at the same time.";
            }
            must "not(current()/../SET_IP_REPLICATION_GROUP)" {
                error-message "QoS and forwarding actions cant be configured at the same time.";
            }
            must "not(current()/../SET_IPV6_NEXTHOP)" {
                error-message "QoS and forwarding actions cant be configured at the same time.";
            }
            must "not(current()/../SET_IPV6_NEXTHOP_GROUP)" {
                error-message "QoS and forwarding actions cant be configured at the same time.";
            }
            must "not(current()/../SET_IPV6_REPLICATION_GROUP)" {
                error-message "QoS and forwarding actions cant be configured at the same time.";
            }
            must "not(current()/../DEFAULT_PACKET_ACTION)" {
                error-message "QoS and forwarding actions cant be configured at the same time.";
            }
            must "not(current()/../SET_TRAP_QUEUE)" {
                error-message "QoS and CoPP actions cant be configured at the same time.";
            }
            when "/sonic-flow-based-services/POLICY_TABLE/POLICY_TABLE_LIST[POLICY_NAME=current()/../POLICY_NAME]/TYPE = 'QOS'";
        }

        leaf SET_PCP {
            type uint8 {
                range "0..7" {
                    error-app-tag invalid-pcp-value;
                    error-message "Invalid PCP value.";
                }
            }
            must "not(current()/../SET_MIRROR_SESSION)" {
                error-message "QoS and monitoring actions cant be configured at the same time.";
            }
            must "not(current()/../SET_INTERFACE)" {
                error-message "QoS and forwarding actions cant be configured at the same time.";
            }
            must "not(current()/../SET_IP_NEXTHOP)" {
                error-message "QoS and forwarding actions cant be configured at the same time.";
            }
            must "not(current()/../SET_IP_NEXTHOP_GROUP)" {
                error-message "QoS and forwarding actions cant be configured at the same time.";
            }
            must "not(current()/../SET_IP_REPLICATION_GROUP)" {
                error-message "QoS and forwarding actions cant be configured at the same time.";
            }
            must "not(current()/../SET_IPV6_NEXTHOP)" {
                error-message "QoS and forwarding actions cant be configured at the same time.";
            }
            must "not(current()/../SET_IPV6_NEXTHOP_GROUP)" {
                error-message "QoS and forwarding actions cant be configured at the same time.";
            }
            must "not(current()/../SET_IPV6_REPLICATION_GROUP)" {
                error-message "QoS and forwarding actions cant be configured at the same time.";
            }
            must "not(current()/../DEFAULT_PACKET_ACTION)" {
                error-message "QoS and forwarding actions cant be configured at the same time.";
            }
            must "not(current()/../SET_TRAP_QUEUE)" {
                error-message "QoS and CoPP actions cant be configured at the same time.";
            }
            when "/sonic-flow-based-services/POLICY_TABLE/POLICY_TABLE_LIST[POLICY_NAME=current()/../POLICY_NAME]/TYPE = 'QOS'";
        }

        leaf SET_TC {
            type uint8 {
                range "0..7" {
                    error-app-tag invalid-traffic-class-value;
                    error-message "Invalid Traffic Class value.";
                }
            }
            must "not(current()/../SET_MIRROR_SESSION)" {
                error-message "QoS and monitoring actions cant be configured at the same time.";
            }
            must "not(current()/../SET_INTERFACE)" {
                error-message "QoS and forwarding actions cant be configured at the same time.";
            }
            must "not(current()/../SET_IP_NEXTHOP)" {
                error-message "QoS and forwarding actions cant be configured at the same time.";
            }
            must "not(current()/../SET_IP_NEXTHOP_GROUP)" {
                error-message "QoS and forwarding actions cant be configured at the same time.";
            }
            must "not(current()/../SET_IP_REPLICATION_GROUP)" {
                error-message "QoS and forwarding actions cant be configured at the same time.";
            }
            must "not(current()/../SET_IPV6_NEXTHOP)" {
                error-message "QoS and forwarding actions cant be configured at the same time.";
            }
            must "not(current()/../SET_IPV6_NEXTHOP_GROUP)" {
                error-message "QoS and forwarding actions cant be configured at the same time.";
            }
            must "not(current()/../SET_IPV6_REPLICATION_GROUP)" {
                error-message "QoS and forwarding actions cant be configured at the same time.";
            }
            must "not(current()/../DEFAULT_PACKET_ACTION)" {
                error-message "QoS and forwarding actions cant be configured at the same time.";
            }
            must "not(current()/../SET_TRAP_QUEUE)" {
                error-message "QoS and CoPP actions cant be configured at the same time.";
            }
            when "/sonic-flow-based-services/POLICY_TABLE/POLICY_TABLE_LIST[POLICY_NAME=current()/../POLICY_NAME]/TYPE = 'QOS'";
        }

        leaf SET_POLICER_CIR {
            type uint64;
            units bps;
            must "not(current()/../SET_PACKET_COLOR)" {
                error-message "Policer CIR and packet color actions cant be configured at the same time.";
            }
            must "not(current()/../SET_MIRROR_SESSION)" {
                error-message "QoS and monitoring actions cant be configured at the same time.";
            }
            must "not(current()/../SET_INTERFACE)" {
                error-message "QoS and forwarding actions cant be configured at the same time.";
            }
            must "not(current()/../SET_IP_NEXTHOP)" {
                error-message "QoS and forwarding actions cant be configured at the same time.";
            }
            must "not(current()/../SET_IP_NEXTHOP_GROUP)" {
                error-message "QoS and forwarding actions cant be configured at the same time.";
            }
            must "not(current()/../SET_IP_REPLICATION_GROUP)" {
                error-message "QoS and forwarding actions cant be configured at the same time.";
            }
            must "not(current()/../SET_IPV6_NEXTHOP)" {
                error-message "QoS and forwarding actions cant be configured at the same time.";
            }
            must "not(current()/../SET_IPV6_NEXTHOP_GROUP)" {
                error-message "QoS and forwarding actions cant be configured at the same time.";
            }
            must "not(current()/../SET_IPV6_REPLICATION_GROUP)" {
                error-message "QoS and forwarding actions cant be configured at the same time.";
            }
            must "not(current()/../DEFAULT_PACKET_ACTION)" {
                error-message "QoS and forwarding actions cant be configured at the same time.";
            }
            must "((not(current()/../SET_TRAP_QUEUE)) and (/sonic-flow-based-services/POLICY_TABLE/POLICY_TABLE_LIST[POLICY_NAME=current()/../POLICY_NAME]/TYPE = 'QOS'))"
                 + "or (/sonic-flow-based-services/POLICY_TABLE/POLICY_TABLE_LIST[POLICY_NAME=current()/../POLICY_NAME]/TYPE = 'ACL_COPP')" {
                error-message "QoS and CoPP actions cant be configured at the same time.";
            }
       }

        leaf SET_POLICER_CBS {
            type uint64;
            units bytes;
            must "(current()/../SET_POLICER_CIR) and (current()/../SET_POLICER_CIR > 0)" {
                error-app-tag cir-not-configured;
                error-message "CBS can't be configured without CIR.";
            }
            must "current()*8 >= current()/../SET_POLICER_CIR" {
                error-app-tag cbs-less-than-cir;
                error-message "CBS must be greater than or equal to CIR";
            }
        }

        leaf SET_POLICER_PIR {
            type uint64;
            units bps;
            must "(current()/../SET_POLICER_CIR) and (current()/../SET_POLICER_CIR > 0)" {
                error-app-tag cir-not-configured;
                error-message "PIR can't be configured without CIR.";
            }
            must "current() >= current()/../SET_POLICER_CIR" {
                error-app-tag pir-less-than-cir;
                error-message "PIR must be greater than or equal to CIR";
            }
        }

        leaf SET_POLICER_PBS {
            type uint64;
            units bytes;
            must "(current()/../SET_POLICER_PIR) and (current()/../SET_POLICER_PIR > 0)" {
                error-app-tag pir-not-configured;
                error-message "PBS can't be configured without PIR.";
            }
            must "current()*8 >= current()/../SET_POLICER_PIR" {
                error-app-tag pbs-less-than-pir;
                error-message "PBS must be greater than or equal to PIR";
            }
            must "(not(current()/../SET_POLICER_CBS)) or (current() >= current()/../SET_POLICER_CBS)" {
                error-app-tag pbs-less-than-cbs;
                error-message "PBS must be greater than or equal to CBS";
            }
        }
    }

    grouping policy-section-monitoring-actions {
        leaf SET_MIRROR_SESSION {
            type leafref {
                path "/sms:sonic-mirror-session/sms:MIRROR_SESSION/sms:MIRROR_SESSION_LIST/sms:name";
            }
            must "not(current()/../SET_PCP)" {
                error-message "QoS and monitoring actions cant be configured at the same time.";
            }
            must "not(current()/../SET_DSCP)" {
                error-message "QoS and monitoring actions cant be configured at the same time.";
            }
            must "not(current()/../SET_ECN)" {
                error-message "QoS and monitoring actions cant be configured at the same time.";
            }
            must "not(current()/../SET_PACKET_COLOR)" {
                error-message "QoS and monitoring actions cant be configured at the same time.";
            }
            must "not(current()/../SET_TC)" {
                error-message "QoS and monitoring actions cant be configured at the same time.";
            }
            must "not(current()/../SET_POLICER_CIR)" {
                error-message "QoS and monitoring actions cant be configured at the same time.";
            }
            must "not(current()/../SET_INTERFACE)" {
                error-message "Monitoring and forwarding actions cant be configured at the same time.";
            }
            must "not(current()/../SET_IP_NEXTHOP)" {
                error-message "Monitoring and forwarding actions cant be configured at the same time.";
            }
            must "not(current()/../SET_IP_NEXTHOP_GROUP)" {
                error-message "Monitoring and forwarding actions cant be configured at the same time.";
            }
            must "not(current()/../SET_IP_REPLICATION_GROUP)" {
                error-message "Monitoring and forwarding actions cant be configured at the same time.";
            }
            must "not(current()/../SET_IPV6_NEXTHOP)" {
                error-message "Monitoring and forwarding actions cant be configured at the same time.";
            }
            must "not(current()/../SET_IPV6_NEXTHOP_GROUP)" {
                error-message "Monitoring and forwarding actions cant be configured at the same time.";
            }
            must "not(current()/../SET_IPV6_REPLICATION_GROUP)" {
                error-message "Monitoring and forwarding actions cant be configured at the same time.";
            }
            must "not(current()/../DEFAULT_PACKET_ACTION)" {
                error-message "Monitoring and forwarding actions cant be configured at the same time.";
            }
            must "not(current()/../SET_TRAP_QUEUE)" {
                error-message "Monitoring and CoPP actions cant be configured at the same time.";
            }
            when "/sonic-flow-based-services/POLICY_TABLE/POLICY_TABLE_LIST[POLICY_NAME=current()/../POLICY_NAME]/TYPE = 'MONITORING'";
        }
    }

    grouping policy-section-forwarding-actions {
        leaf-list SET_INTERFACE {
            max-elements 64;
            type string {
                /* The format will be Ethernet<Id>|<Prio> OR PortChannel<ID>|<Prio OR Eth1/<Id>[/<Id>]|<Prio> */
                pattern '((Ethernet([1-3][0-9]{3}|[1-9][0-9]{2}|[1-9][0-9]|[0-9]))|(Eth1/[1-9][0-9]{0,2}(/[1-9][0-9]{0,1})?)|(PortChannel([1-9]|[1-9][0-9]|1[0-9][0-9]|2[0-4][0-9]|25[0-6])))\|'
                    + '([1-9][0-9]{0,3}|[1-5][0-9]{4}|6[0-4][0-9]{3}|65[0-4][0-9]{2}|655[0-2][0-9]|6553[0-5])?';
            }
            sonic-ext:custom-validation ValidateEgressConfig;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_IP_NEXTHOP)" {
                error-message "L2 and IPv4 forwarding actions cant be configured at the same time.";
            }
            must "not(current()/../SET_IP_NEXTHOP_GROUP)" {
                error-message "L2 and IPv4 forwarding actions cant be configured at the same time.";
            }
            must "not(current()/../SET_IP_REPLICATION_GROUP)" {
                error-message "L2 and IPv4 forwarding actions cant be configured at the same time.";
            }
            must "not(current()/../SET_IPV6_NEXTHOP)" {
                error-message "L2 and IPv6 forwarding actions cant be configured at the same time.";
            }
            must "not(current()/../SET_IPV6_NEXTHOP_GROUP)" {
                error-message "L2 and IPv6 forwarding actions cant be configured at the same time.";
            }
            must "not(current()/../SET_IPV6_REPLICATION_GROUP)" {
                error-message "L2 and IPv6 forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for L2 forwarding. Each leaf is in the format <PortName>|<Priority>.
                Priority can be empty as its optional";
        }

        leaf-list SET_IP_NEXTHOP {
            max-elements 64;
            type string {
                pattern '((([0-9]|[1-9][0-9]|1[0-9][0-9]|2[0-4][0-9]|25[0-5])\.){3}([0-9]|[1-9][0-9]|1[0-9][0-9]|2[0-4][0-9]|25[0-5]))\|'
                    + '(default|Vrf[a-zA-Z0-9_-]+)?\|'
                    + '([1-9][0-9]{0,3}|[1-5][0-9]{4}|6[0-4][0-9]{3}|65[0-4][0-9]{2}|655[0-2][0-9]|6553[0-5])?';
            }
            sonic-ext:custom-validation ValidateEgressConfig;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_INTERFACE)" {
                error-message "L2 and IPv4 forwarding actions cant be configured at the same time.";
            }
            must "not(current()/../SET_IPV6_NEXTHOP)" {
                error-message "IPv4 and IPv6 forwarding actions cant be configured at the same time.";
            }
            must "not(current()/../SET_IPV6_NEXTHOP_GROUP)" {
                error-message "IPv4 and IPv6 forwarding actions cant be configured at the same time.";
            }
            must "not(current()/../SET_IPV6_REPLICATION_GROUP)" {
                error-message "IPv4 and IPv6 and forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for IPv4 forwarding. Each leaf is in the format <IPv4Address>|<VRF>|<Priority>.
                Priority and VRF can be empty as its optional";
        }

        leaf-list SET_IPV6_NEXTHOP {
            max-elements 64;
            type string {
                pattern '(((:|[0-9a-fA-F]{0,4}):)([0-9a-fA-F]{0,4}:){0,5}(([0-9a-fA-F]{0,4}:)?(:|[0-9a-fA-F]{0,4})))\|'
                    + '(default|Vrf[a-zA-Z0-9_-]+)?\|'
                    + '([1-9][0-9]{0,3}|[1-5][0-9]{4}|6[0-4][0-9]{3}|65[0-4][0-9]{2}|655[0-2][0-9]|6553[0-5])?';
            }
            sonic-ext:custom-validation ValidateEgressConfig;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_INTERFACE)" {
                error-message "L2 and IPv6 forwarding actions cant be configured at the same time.";
            }
            must "not(current()/../SET_IP_NEXTHOP)" {
                error-message "IPV6 and IPv4 forwarding actions cant be configured at the same time.";
            }
            must "not(current()/../SET_IP_NEXTHOP_GROUP)" {
                error-message "IPV6 and IPv4 forwarding actions cant be configured at the same time.";
            }
            must "not(current()/../SET_IP_REPLICATION_GROUP)" {
                error-message "IPv6 and IPv4 forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for IPv6 forwarding. Each leaf is in the format <IPv6Address>|<VRF>|<Priority>.
                Priority and VRF can be empty as its optional";
        }

        leaf DEFAULT_PACKET_ACTION {
            type enumeration {
                enum DROP;
            }
            when "/sonic-flow-based-services/POLICY_TABLE/POLICY_TABLE_LIST[POLICY_NAME=current()/../POLICY_NAME]/TYPE = 'FORWARDING'";
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_TRAP_QUEUE)" {
                error-message "Forwarding and CoPP actions cant be configured at the same time.";
            }
        }

        leaf-list SET_IP_NEXTHOP_GROUP {
            max-elements 64;
            type string {
                pattern '[a-zA-Z0-9]{1}([-a-zA-Z0-9_]{0,71})\|'
                    + '([1-9][0-9]{0,3}|[1-5][0-9]{4}|6[0-4][0-9]{3}|65[0-4][0-9]{2}|655[0-2][0-9]|6553[0-5])?';
            }
            sonic-ext:custom-validation ValidateGroupTypeMatches;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_INTERFACE)" {
                error-message "L2 and IPv4 forwarding actions cant be configured at the same time.";
            }
            must "not(current()/../SET_IPV6_NEXTHOP)" {
                error-message "IPv4 and IPv6 forwarding actions cant be configured at the same time.";
            }
            must "not(current()/../SET_IPV6_NEXTHOP_GROUP)" {
                error-message "IPv4 and IPv6 forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for IPv4 forwarding. Each leaf is in the format <NHGroupName>|<Priority>.
                Priority can be empty as its optional";
        }

        leaf-list SET_IPV6_NEXTHOP_GROUP {
            max-elements 64;
            type string {
                pattern '[a-zA-Z0-9]{1}([-a-zA-Z0-9_]{0,71})\|'
                    + '([1-9][0-9]{0,3}|[1-5][0-9]{4}|6[0-4][0-9]{3}|65[0-4][0-9]{2}|655[0-2][0-9]|6553[0-5])?';
            }
            sonic-ext:custom-validation ValidateGroupTypeMatches;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_INTERFACE)" {
                error-message "L2 and IPv6 forwarding actions cant be configured at the same time.";
            }
            must "not(current()/../SET_IP_NEXTHOP)" {
                error-message "IPv4 and IPv6 forwarding actions cant be configured at the same time.";
            }
            must "not(current()/../SET_IP_NEXTHOP_GROUP)" {
                error-message "IPv4 and IPv6 forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for IPv4 forwarding. Each leaf is in the format <NHGroupName>|<Priority>.
                Priority can be empty as its optional";
        }

        leaf-list SET_IP_REPLICATION_GROUP {
            max-elements 64;
            type string {
                pattern '[a-zA-Z0-9]{1}([-a-zA-Z0-9_]{0,71})\|'
                    + '([1-9][0-9]{0,3}|[1-5][0-9]{4}|6[0-4][0-9]{3}|65[0-4][0-9]{2}|655[0-2][0-9]|6553[0-5])?';
            }
            sonic-ext:custom-validation ValidateGroupTypeMatches;
            sonic-ext:custom-validation ValidateAclReplSupported;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_INTERFACE)" {
                error-message "L2 and IPv4 forwarding actions cant be configured at the same time.";
            }
            must "not(current()/../SET_IPV6_NEXTHOP)" {
                error-message "IPv4 and IPv6 forwarding actions cant be configured at the same time.";
            }
            must "not(current()/../SET_IPV6_NEXTHOP_GROUP)" {
                error-message "IPv4 and IPv6 forwarding actions cant be configured at the same time.";
            }
            must "not(current()/../SET_IPV6_REPLICATION_GROUP)" {
                error-message "IPv4 and IPv6 forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for IPv4 forwarding. Each leaf is in the format <NHGroupName>|<Priority>.
                Priority can be empty as its optional";
        }

        leaf-list SET_IPV6_REPLICATION_GROUP {
            max-elements 64;
            type string {
                pattern '[a-zA-Z0-9]{1}([-a-zA-Z0-9_]{0,71})\|'
                    + '([1-9][0-9]{0,3}|[1-5][0-9]{4}|6[0-4][0-9]{3}|65[0-4][0-9]{2}|655[0-2][0-9]|6553[0-5])?';
            }
            sonic-ext:custom-validation ValidateGroupTypeMatches;
            sonic-ext:custom-validation ValidateAclReplSupported;
            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
                error-message "Monitoring and forwarding actions cant be configured at the same time.";
            }
            must "not(current()/../SET_INTERFACE)" {
                error-message "L2 and IPv6 forwarding actions cant be configured at the same time.";
            }
            must "not(current()/../SET_IP_NEXTHOP)" {
                error-message "IPv4 and IPv6 forwarding actions cant be configured at the same time.";
            }
            must "not(current()/../SET_IP_NEXTHOP_GROUP)" {
                error-message "IPv4 and IPv6 forwarding actions cant be configured at the same time.";
            }
            must "not(current()/../SET_IP_REPLICATION_GROUP)" {
                error-message "IPv4 and IPv6 forwarding actions cant be configured at the same time.";
            }
            must "not(current()/../SET_TRAP_QUEUE)" {
                error-message "Forwarding and CoPP actions cant be configured at the same time.";
            }
            when "/sonic-flow-based-services/POLICY_TABLE/POLICY_TABLE_LIST[POLICY_NAME=current()/../POLICY_NAME]/TYPE = 'FORWARDING'";
            description "Egress options for IPv4 forwarding. Each leaf is in the format <NHGroupName>|<Priority>.
                Priority can be empty as its optional";
        }

        leaf SET_ARS_DISABLE {
            type boolean;
            when "/sonic-flow-based-services/POLICY_TABLE/POLICY_TABLE_LIST[POLICY_NAME=current()/../POLICY_NAME]/TYPE = 'FORWARDING'";

            must "not(current()/../SET_PCP)" {
                error-message "QoS and forwarding actions cant be configured at the same time.";
            }
            must "not(current()/../SET_DSCP)" {
                error-message "QoS and forwarding actions cant be configured at the same time.";
            }
            must "not(current()/../SET_ECN)" {
                error-message "QoS and forwarding actions cant be configured at the same time.";
            }
            must "not(current()/../SET_PACKET_COLOR)" {
                error-message "QoS and forwarding actions cant be configured at the same time.";
            }
            must "not(current()/../SET_TC)" {
                error-message "QoS and forwarding actions cant be configured at the same time.";
            }
            must "not(current()/../SET_POLICER_CIR)" {
                error-message "QoS and forwarding actions cant be configured at the same time.";
            }
            must "not(current()/../SET_MIRROR_SESSION)" {
               error-message "Monitoring and forwarding actions cant be configured at the same time.";
            }
            must "not(current()/../SET_TRAP_QUEUE)" {
                error-message "Forwarding and CoPP actions cant be configured at the same time.";
            }
            must "not(current()/../DEFAULT_PACKET_ACTION)" {
                error-message "ARS forwarding disable action cant be combined with other Forwarding actions.";
            }
            must "not(current()/../SET_IP_NEXTHOP)" {
                error-message "ARS forwarding disable action cant be combined with other Forwarding actions.";
            }
            must "not(current()/../SET_IPV6_NEXTHOP)" {
                error-message "ARS forwarding disable action cant be combined with other Forwarding actions.";
            }
            must "not(current()/../SET_IP_NEXTHOP_GROUP)" {
                error-message "ARS forwarding disable action cant be combined with other Forwarding actions.";
            }
            must "not(current()/../SET_IPV6_NEXTHOP_GROUP)" {
                error-message "ARS forwarding disable action cant be combined with other Forwarding actions.";
            }
            must "not(current()/../SET_IP_REPLICATION_GROUP)" {
                error-message "ARS forwarding disable action cant be combined with other Forwarding actions.";
            }
            must "not(current()/../SET_IPV6_REPLICATION_GROUP)" {
                error-message "ARS forwarding disable action cant be combined with other Forwarding actions.";
            }
        }
    }

    grouping policy-section-acl-copp-actions {
        leaf SET_TRAP_QUEUE {
            type uint8 {
                range "0..31" {
                    error-app-tag invalid-trap-queue-value;
                    error-message "Invalid Trap queue value.";
                }
            }
            sonic-ext:custom-validation ValidateCpuQueueId;
            must "not(current()/../SET_PCP)" {
                error-message "CoPP and QoS actions cant be configured at the same time.";
            }
            must "not(current()/../SET_DSCP)" {
                error-message "CoPP and QoS actions cant be configured at the same time.";
            }
            must "not(current()/../SET_ECN)" {
                error-message "CoPP and QoS actions cant be configured at the same time.";
            }
            must "not(current()/../SET_PACKET_COLOR)" {
                error-message "CoPP and QoS actions cant be configured at the same time.";
            }
            must "not(current()/../SET_TC)" {
                error-message "CoPP and QoS actions cant be configured at the same time.";
            }
            must "not(current()/../SET_MIRROR_SESSION)" {
                error-message "CoPP and monitoring actions cant be configured at the same time.";
            }
            must "not(current()/../SET_INTERFACE)" {
                error-message "CoPP and forwarding actions cant be configured at the same time.";
            }
            must "not(current()/../SET_IP_NEXTHOP)" {
                error-message "CoPP and forwarding actions cant be configured at the same time.";
            }
            must "not(current()/../SET_IP_NEXTHOP_GROUP)" {
                error-message "CoPP and forwarding actions cant be configured at the same time.";
            }
            must "not(current()/../SET_IP_REPLICATION_GROUP)" {
                error-message "CoPP and forwarding actions cant be configured at the same time.";
            }
            must "not(current()/../SET_IPV6_NEXTHOP)" {
                error-message "CoPP and forwarding actions cant be configured at the same time.";
            }
            must "not(current()/../SET_IPV6_NEXTHOP_GROUP)" {
                error-message "CoPP and forwarding actions cant be configured at the same time.";
            }
            must "not(current()/../SET_IPV6_REPLICATION_GROUP)" {
                error-message "CoPP and forwarding actions cant be configured at the same time.";
            }
            must "not(current()/../DEFAULT_PACKET_ACTION)" {
                error-message "CoPP and forwarding actions cant be configured at the same time.";
            }
            when "/sonic-flow-based-services/POLICY_TABLE/POLICY_TABLE_LIST[POLICY_NAME=current()/../POLICY_NAME]/TYPE = 'ACL_COPP'";
        }
    }

    grouping policy-attributes {
        leaf DESCRIPTION {
            type string {
                length 1..256 {
                    error-app-tag policy-description-invalid-length;
                }
            }
        }

        leaf TYPE {
            type policy-types;
            mandatory true;
            sonic-ext:custom-validation ValidateLeafConstant;
        }
    }

    container sonic-flow-based-services {
        container POLICY_TABLE {
            list POLICY_TABLE_LIST {
                key "POLICY_NAME";
                max-elements 256;

                leaf POLICY_NAME {
                    type string {
                        pattern '[a-zA-Z0-9]{1}([-a-zA-Z0-9_]{0,62})';
                        length 1..63;
                    }
                }

                leaf DESCRIPTION {
                    type string {
                        length 1..256 {
                            error-app-tag policy-description-invalid-length;
                        }
                    }
                }

                leaf TYPE {
                    mandatory true;
                    sonic-ext:custom-validation ValidateLeafConstant;
                    type policy-types;
                }
            }
        }

        container CLASSIFIER_TABLE {
            list CLASSIFIER_TABLE_LIST {
                key "CLASSIFIER_NAME";
                max-elements 256;

                leaf CLASSIFIER_NAME {
                    type string {
                        pattern '[a-zA-Z0-9]{1}([-a-zA-Z0-9_]{0,62})';
                        length 1..63;
                    }

                    must "current() != 'default'" {
                        error-app-tag name-not-allowed;
                        error-message "'default' name is not allowed";
                    }
                }

                uses classifier-attributes;
            }
        }

        container POLICY_SECTIONS_TABLE {
            list POLICY_SECTIONS_TABLE_LIST {
                key "POLICY_NAME CLASSIFIER_NAME";

                leaf POLICY_NAME {
                    type leafref {
                        path "/sonic-flow-based-services/POLICY_TABLE/POLICY_TABLE_LIST/POLICY_NAME";
                    }
                }

                leaf CLASSIFIER_NAME {
                    type leafref {
                        path "/sonic-flow-based-services/CLASSIFIER_TABLE/CLASSIFIER_TABLE_LIST/CLASSIFIER_NAME";
                    }
                }

                uses policy-section-attributes;
                uses policy-section-qos-actions;
                uses policy-section-monitoring-actions;
                uses policy-section-forwarding-actions;
                uses policy-section-acl-copp-actions;
            }
        }

        container POLICY_BINDING_TABLE {
            list POLICY_BINDING_TABLE_LIST {
                key INTERFACE_NAME;

                leaf INTERFACE_NAME {
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/sint:sonic-interface/sint:VLAN_SUB_INTERFACE/sint:VLAN_SUB_INTERFACE_LIST/sint:id";
                        }
                        type enumeration {
                            enum Switch;
                            enum CtrlPlane;
                            enum CPU;
                        }
                    }
                }

                leaf INGRESS_QOS_POLICY {
                    must "/sonic-flow-based-services/POLICY_TABLE/POLICY_TABLE_LIST[POLICY_NAME=current()]/TYPE = 'QOS'" {
                        error-app-tag policy-not-qos-type;
                        error-message "Policy is not of type qos";
                    }
                    type leafref {
                        path "/sonic-flow-based-services/POLICY_TABLE/POLICY_TABLE_LIST/POLICY_NAME";
                    }
                    sonic-ext:custom-validation ValidateLeafConstant;
                }
                leaf EGRESS_QOS_POLICY {
                    must "/sonic-flow-based-services/POLICY_TABLE/POLICY_TABLE_LIST[POLICY_NAME=current()]/TYPE = 'QOS'" {
                        error-app-tag policy-not-qos-type;
                        error-message "Policy is not of type qos";
                    }
                    type leafref {
                        path "/sonic-flow-based-services/POLICY_TABLE/POLICY_TABLE_LIST/POLICY_NAME";
                    }
                    sonic-ext:custom-validation ValidateLeafConstant;
                }
                leaf INGRESS_MONITORING_POLICY {
                    must "/sonic-flow-based-services/POLICY_TABLE/POLICY_TABLE_LIST[POLICY_NAME=current()]/TYPE = 'MONITORING'" {
                        error-app-tag policy-not-monitoring-type;
                        error-message "Policy is not of type monitoring";
                    }
                    type leafref {
                        path "/sonic-flow-based-services/POLICY_TABLE/POLICY_TABLE_LIST/POLICY_NAME";
                    }
                    sonic-ext:custom-validation ValidateLeafConstant;
                }
                leaf INGRESS_FORWARDING_POLICY {
                    must "/sonic-flow-based-services/POLICY_TABLE/POLICY_TABLE_LIST[POLICY_NAME=current()]/TYPE = 'FORWARDING'" {
                        error-app-tag policy-not-forwarding-type;
                        error-message "Policy is not of type forwarding";
                    }
                    type leafref {
                        path "/sonic-flow-based-services/POLICY_TABLE/POLICY_TABLE_LIST/POLICY_NAME";
                    }
                    sonic-ext:custom-validation ValidateLeafConstant;
                }
                leaf INGRESS_ACL_COPP_POLICY {
                    must "/sonic-flow-based-services/POLICY_TABLE/POLICY_TABLE_LIST[POLICY_NAME=current()]/TYPE = 'ACL_COPP'" {
                        error-app-tag policy-not-acl-copp-type;
                        error-message "Policy is not of type acl-copp";
                    }
                    type leafref {
                        path "/sonic-flow-based-services/POLICY_TABLE/POLICY_TABLE_LIST/POLICY_NAME";
                    }
                    sonic-ext:custom-validation ValidateLeafConstant;
                }
            }
        }

        container PBF_NEXTHOP_GROUP {
            list PBF_NEXTHOP_GROUP_LIST {
                key GROUP_NAME;
                max-elements 256;

                leaf GROUP_NAME {
                    type string {
                        pattern '[a-zA-Z0-9]{1}([-a-zA-Z0-9_]{0,62})';
                        length 1..63;
                    }
                }

                leaf DESCRIPTION {
                    type string {
                        length 1..256 {
                            error-app-tag pbf-nhgroup-description-invalid-length;
                        }
                    }
                }

                leaf TYPE {
                    mandatory true;
                    sonic-ext:custom-validation ValidateLeafConstant;
                    type pbf-next-hop-group-type;
                }

                leaf THRESHOLD_TYPE {
                    type enumeration {
                        enum PERCENTAGE;
                        enum COUNT;
                    }
                }

                leaf THRESHOLD_UP {
                    type uint8;
                    must "(not(current()/../THRESHOLD_TYPE)) or (current()/../THRESHOLD_TYPE = 'COUNT') or ((current()/../THRESHOLD_TYPE = 'PERCENTAGE') and (current() >= 1) and (current() <= 100))" {
                        error-app-tag invalid-value-threshold-up;
                        error-message "Threshold up percentage value not in range 1-100";
                    }
                    must "(not(current()/../THRESHOLD_TYPE)) or (current()/../THRESHOLD_TYPE = 'PERCENTAGE') or ((current()/../THRESHOLD_TYPE = 'COUNT') and (current() >= 1) and (current() <= 128))" {
                        error-app-tag invalid-value-threshold-up;
                        error-message "Threshold up count value not in range 1-128";
                    }
                    must "(not(current()/../THRESHOLD_DOWN) or (current() > current()/../THRESHOLD_DOWN))" {
                        error-app-tag threshold-up-less-than-threshold-down;
                        error-message "Threshold up value must be greater than threshold down value";
                    }
                    must "(current()/../THRESHOLD_TYPE = 'COUNT') or (current()/../THRESHOLD_TYPE = 'PERCENTAGE')" {
                        error-app-tag "threshold-type-not-configured";
                        error-message "Threshold type mandatory to configure threshold up or down values.";
                    }
                }

                leaf THRESHOLD_DOWN {
                    type uint8;
                    must "(not(current()/../THRESHOLD_TYPE)) or (current()/../THRESHOLD_TYPE = 'COUNT') or ((current()/../THRESHOLD_TYPE = 'PERCENTAGE') and (current() >= 0) and (current() <= 99))" {
                        error-app-tag invalid-value-threshold-down;
                        error-message "Threshold down percentage value not in range 0-99";
                    }
                    must "(not(current()/../THRESHOLD_TYPE)) or (current()/../THRESHOLD_TYPE = 'PERCENTAGE') or ((current()/../THRESHOLD_TYPE = 'COUNT') and (current() >= 0) and (current() <= 127))" {
                        error-app-tag invalid-value-threshold-down;
                        error-message "Threshold down count value not in range 1-127";
                    }
                    must "(not(current()/../THRESHOLD_UP) or (current() < current()/../THRESHOLD_UP))" {
                        error-app-tag threshold-down-greater-than-threshold-up;
                        error-message "Threshold down value must be lesser than threshold up value";
                    }
                    must "(current()/../THRESHOLD_TYPE = 'COUNT') or (current()/../THRESHOLD_TYPE = 'PERCENTAGE')" {
                        error-app-tag "threshold-type-not-configured";
                        error-message "Threshold type mandatory to configure threshold up or down values.";
                    }
                }

                leaf-list SET_IP_NEXTHOP {
                    max-elements 128;
                    type string {
                        pattern '([1-9][0-9]{0,3}|[1-5][0-9]{4}|6[0-4][0-9]{3}|65[0-4][0-9]{2}|655[0-2][0-9]|6553[0-5])\|'
                            + '((([0-9]|[1-9][0-9]|1[0-9][0-9]|2[0-4][0-9]|25[0-5])\.){3}([0-9]|[1-9][0-9]|1[0-9][0-9]|2[0-4][0-9]|25[0-5]))\|'
                            + '(default|Vrf[a-zA-Z0-9_-]+)?\|'
                            + '((non-recursive)|(recursive)|(overlay))?';
                    }
                    must "current()/../TYPE = 'IPV4'" {
                        error-app-tag not-ipv4-next-hop;
                        error-message "Only IPv4 next-hops can be configured for IPv4 next-hop groups";
                    }
                }

                leaf-list SET_IPV6_NEXTHOP {
                    max-elements 128;
                    type string {
                        pattern '([1-9][0-9]{0,3}|[1-5][0-9]{4}|6[0-4][0-9]{3}|65[0-4][0-9]{2}|655[0-2][0-9]|6553[0-5])\|'
                            + '(((:|[0-9a-fA-F]{0,4}):)([0-9a-fA-F]{0,4}:){0,5}(([0-9a-fA-F]{0,4}:)?(:|[0-9a-fA-F]{0,4})))\|'
                            + '(default|Vrf[a-zA-Z0-9_-]+)?\|'
                            + '((non-recursive)|(recursive)|(overlay))?';
                    }
                    must "current()/../TYPE = 'IPV6'" {
                        error-app-tag not-ipv6-next-hop;
                        error-message "Only IPv6 next-hops can be configured for IPv6 next-hop groups";
                    }
                }
            }
        }

        container PBF_REPLICATION_GROUP {
            list PBF_REPLICATION_GROUP_LIST {
                key GROUP_NAME;
                max-elements 256;

                leaf GROUP_NAME {
                    type string {
                        pattern '[a-zA-Z0-9]{1}([-a-zA-Z0-9_]{0,62})';
                        length 1..63;
                    }
                }

                leaf DESCRIPTION {
                    type string {
                        length 1..256 {
                            error-app-tag pbf-replication-group-description-invalid-length;
                        }
                    }
                }

                leaf TYPE {
                    mandatory true;
                    sonic-ext:custom-validation ValidateLeafConstant;
                    sonic-ext:custom-validation ValidateAclReplSupported;
                    type pbf-replication-group-type;
                }

                leaf-list SET_IP_NEXTHOP {
                    max-elements 128;
                    type string {
                        pattern '([1-9][0-9]{0,3}|[1-5][0-9]{4}|6[0-4][0-9]{3}|65[0-4][0-9]{2}|655[0-2][0-9]|6553[0-5])\|'
                            + '((([0-9]|[1-9][0-9]|1[0-9][0-9]|2[0-4][0-9]|25[0-5])\.){3}([0-9]|[1-9][0-9]|1[0-9][0-9]|2[0-4][0-9]|25[0-5]))\|'
                            + '(default|Vrf[a-zA-Z0-9_-]+)?\|'
                            + '((non-recursive)|(recursive)|(overlay))?\|'
                            + '(single-copy)?';
                    }
                    sonic-ext:custom-validation ValidateNextHopIp;
                    must "current()/../TYPE = 'IPV4'" {
                        error-app-tag not-ipv4-next-hop;
                        error-message "Only IPv4 next-hops can be configured for IPv4 next-hop groups";
                    }
                }

                leaf-list SET_IPV6_NEXTHOP {
                    max-elements 128;
                    type string {
                        pattern '([1-9][0-9]{0,3}|[1-5][0-9]{4}|6[0-4][0-9]{3}|65[0-4][0-9]{2}|655[0-2][0-9]|6553[0-5])\|'
                            + '(((:|[0-9a-fA-F]{0,4}):)([0-9a-fA-F]{0,4}:){0,5}(([0-9a-fA-F]{0,4}:)?(:|[0-9a-fA-F]{0,4})))\|'
                            + '(default|Vrf[a-zA-Z0-9_-]+)?\|'
                            + '((non-recursive)|(recursive)|(overlay))?\|'
                            + '(single-copy)?';
                    }
                    sonic-ext:custom-validation ValidateNextHopIp;
                    must "current()/../TYPE = 'IPV6'" {
                        error-app-tag not-ipv6-next-hop;
                        error-message "Only IPv6 next-hops can be configured for IPv6 next-hop groups";
                    }
                }
            }
        }
    }


    // RPCs related

    // Groupings needed for RPCs
    grouping pbf-egress-intf-config-attributes {
        leaf INTERFACE_NAME {
            type string;
        }

        leaf PRIORITY {
            type uint16;
        }
    }

    grouping pbf-nexthop-config-attributes {
        leaf IP_ADDRESS {
            type string;
        }

        leaf VRF {
            type string;
        }

        leaf PRIORITY {
            type uint16;
        }
    }

    grouping pbf-nexthop-group-attributes {
        leaf GROUP_NAME {
            type string;
        }

        leaf PRIORITY {
            type uint16;
        }
    }
    
    grouping pbf-replication-group-attributes {
        leaf GROUP_NAME {
            type string;
        }

        leaf PRIORITY {
            type uint16;
        }
    }

    // RPCs
    rpc get-classifier {
        description
            "RPC to retrieve the classifier data. The name and match-type are optional. If no name is specified then all
            classifiers with the matching match-type will be retrieved. If no match-type is provided then all
            classifiers will be retrieved.";

        input {
            leaf CLASSIFIER_NAME {
                type string;
                description
                    "Classifier Name to be retrieved. (Optional)";
            }
            leaf MATCH_TYPE {
                type classifier-match-type;
                description
                    "Retrieve the classifier using match-type.";
            }
        }
        output {
            list CLASSIFIERS {
                key "CLASSIFIER_NAME";

                leaf CLASSIFIER_NAME {
                    type string;
                    description
                        "Classifier name";
                }

                uses classifier-attributes;

                leaf TRAP_IDS {
                    type string;
                    description
                        "Comma separated list of trap_ids";
                }

                list REFERENCES {
                    leaf POLICY_NAME {
                        type string;
                        description
                            "Policy name referring this classifier";
                    }
                    uses policy-section-attributes;
                }
            }
        }
    }

    rpc get-policy {
        description
            "RPC to retrieve the policy data. The policy name, policy type and class name are optional. If no policy name is specified then all
            policies with the matching type will be retrieved. If no policy type is provided then all policies will
            be retrieved. Class name is valid only when policy name is valid.";

        input {
            leaf POLICY_NAME {
                type string;
                description
                    "Name of the policy to retrieved. (Optional)";
            }
            leaf TYPE {
                type policy-types;
                description
                    "Type of the policy to retrieved. (Optional)";
            }
            leaf CLASS_NAME {
                type string;
                description
                    "Name of the flow classifier using this policy to retrieved. (Optional)";
            }
        }
        output {
            list POLICIES {
                key "POLICY_NAME";

                leaf POLICY_NAME {
                    type string;
                }

                uses policy-attributes;

                list FLOWS {
                    leaf CLASS_NAME {
                        type string;
                        description
                            "Classifier using this policy";
                    }

                    leaf DESCRIPTION {
                        type string;
                    }

                    leaf PRIORITY {
                        type uint16;
                    }

                    leaf SET_DSCP {
                        type uint8;
                    }

                    leaf SET_ECN {
                        type uint8;
                    }

                    leaf SET_PACKET_COLOR {
                        type packet-color-types;
                    }

                    leaf SET_PCP {
                        type uint8;
                    }

                    leaf SET_TC {
                        type uint8;
                    }

                    leaf SET_POLICER_CIR {
                        type uint64;
                    }

                    leaf SET_POLICER_CBS {
                        type uint64;
                    }

                    leaf SET_POLICER_PIR {
                        type uint64;
                    }

                    leaf SET_POLICER_PBS {
                        type uint64;
                    }

                    leaf SET_MIRROR_SESSION {
                        type string;
                    }

                    list SET_INTERFACE {
                        uses pbf-egress-intf-config-attributes;
                    }

                    list SET_IP_NEXT_HOP {
                        uses pbf-nexthop-config-attributes;
                    }

                    list SET_IP_NEXTHOP_GROUP {
                        uses pbf-nexthop-group-attributes;
                    }

                    list SET_IP_REPLICATION_GROUP {
                        uses pbf-replication-group-attributes;
                    }

                    list SET_IPV6_NEXT_HOP {
                        uses pbf-nexthop-config-attributes;
                    }

                    list SET_IPV6_NEXTHOP_GROUP {
                        uses pbf-nexthop-group-attributes;
                    }

                    list SET_IPV6_REPLICATION_GROUP {
                        uses pbf-replication-group-attributes;
                    }

                    leaf DEFAULT_PACKET_ACTION {
                        type enumeration {
                            enum DROP;
                        }
                    }

                    leaf TRAP_GROUP {
                        type string;
                        description "CoPP trap group name";
                    }

                    leaf TRAP_ACTION {
                        type string {
                            pattern "(drop)|(forward)|(copy)|(copy_cancel)|(trap)|(log)|(deny)|(transit)" {
                                error-message "Invalid value passed for trap_action";
                            }
                        }
                        description
                            "Trap action";
                    }

                    leaf TRAP_PRIORITY {
                        type uint16 {
                            range "0..1023" {
                                error-message "Invalid value passed for trap_priority";
                            }
                        }
                        description
                            "Priority value";
                    }

                    leaf QUEUE {
                        type uint8 {
                            range "0..47" {
                                error-message "Invalid value passed for queue";
                            }
                        }
                        description
                            "CPU queue id";
                    }

                    leaf METER_TYPE {
                        type string {
                            pattern "(packets)|(bytes)" {
                                error-message "Invalid value passed for meter_type";
                            }
                        }
                        description
                            "Meter type";
                    }

                    leaf MODE {
                        type string {
                            pattern "(sr_tcm)|(tr_tcm)|(storm)" {
                                error-message "Invalid value passed for mode";
                            }
                        }
                        description
                            "Mode";
                    }

                    leaf GREEN_ACTION {
                        type string {
                            pattern "(drop)|(forward)|(copy)|(copy_cancel)|(trap)|(log)|(deny)|(transit)" {
                                error-message "Invalid value passed for green_action";
                            }
                        }
                        description
                            "Green action";
                    }

                    leaf RED_ACTION {
                        type string {
                            pattern "(drop)|(forward)|(copy)|(copy_cancel)|(trap)|(log)|(deny)|(transit)" {
                                error-message "Invalid value passed for red_action";
                            }
                        }
                        description
                            "Red action";
                    }

                    leaf YELLOW_ACTION {
                        type string {
                            pattern "(drop)|(forward)|(copy)|(copy_cancel)|(trap)|(log)|(deny)|(transit)" {
                                error-message "Invalid value passed for yellow_action";
                            }
                        }
                        description
                            "Yellow action";
                    }
                }

                list APPLIED_INTERFACES {
                    leaf INTERFACE_NAME {
                        type string;
                        description
                            "Interface name on which the policy is applied.";
                    }

                    leaf STAGE {
                        type policy-binding-stages;
                        description
                            "Policy binding direction ingress/egress";
                    }
                }
            }
        }
    }

    rpc get-service-policy {
        description
            "Reprieves the Operational state of the policy application on interface like match counters,
            policer counters for QoS policies, selected next-hop for forwarding policies etc. Policy name or
            Interface name is mandatory. The following list shows the different combination supported

            Policy Name only:: Operational data for all applications of the policy
            Intf Name only:: Operational data for all policies applied for the interface.
            Type only:: Not supported.
            Policy Name + Intf Name:: Operational data for specific application of the policy to interface.
            Policy Name + Type:: Same as specifying just policy name but with added validation for type match.
            Intf Name + Type:: Operational data for specified policy type on the interface.
            Policy Name + Intf Name + Type:: Same as Policy Name + Intf Name but added validation for type match.";

        input {
            leaf POLICY_NAME {
                type string;
                description
                    "Name of the policy to retrieved.";
            }
            leaf INTERFACE_NAME {
                type string;
                description
                    "Interface name on which the policy is applied.";
            }
            leaf TYPE {
                type policy-types;
                description
                    "Type of the policy to retrieved. (Optional)";
            }
        }
        output {
            list INTERFACES {
                key "INTERFACE_NAME";

                leaf INTERFACE_NAME {
                    type string;
                }

                list APPLIED_POLICIES {
                    leaf POLICY_NAME {
                        type string;
                    }

                    leaf STAGE {
                        type policy-binding-stages;
                        description
                            "Policy binding direction ingress/egress";
                    }

                    uses policy-attributes;

                    list FLOWS {
                        leaf CLASS_NAME {
                            type string;
                            description
                                "Classifier using this policy";
                        }

                        leaf DESCRIPTION {
                            type string;
                        }

                        leaf PRIORITY {
                            type uint16;
                        }

                        leaf SET_DSCP {
                            type uint8;
                        }

                        leaf SET_ECN {
                            type uint8;
                        }

                        leaf SET_PACKET_COLOR {
                            type packet-color-types;
                        }

                        leaf SET_PCP {
                            type uint8;
                        }

                        leaf SET_TC {
                            type uint8;
                        }

                        leaf SET_POLICER_CIR {
                            type uint64;
                        }

                        leaf SET_POLICER_CBS {
                            type uint64;
                        }

                        leaf SET_POLICER_PIR {
                            type uint64;
                        }

                        leaf SET_POLICER_PBS {
                            type uint64;
                        }

                        leaf SET_MIRROR_SESSION {
                            type string;
                        }

                        list SET_INTERFACE {
                            uses pbf-egress-intf-config-attributes;
                        }

                        list SET_IP_NEXT_HOP {
                            uses pbf-nexthop-config-attributes;
                        }

                        list SET_IP_NEXTHOP_GROUP {
                            uses pbf-nexthop-group-attributes;
                        }

                        list SET_IPV6_NEXT_HOP {
                            uses pbf-nexthop-config-attributes;
                        }

                        list SET_IPV6_NEXTHOP_GROUP {
                            uses pbf-nexthop-group-attributes;
                        }

                        leaf DEFAULT_PACKET_ACTION {
                            type enumeration {
                                enum DROP;
                            }
                        }

                        leaf SET_TRAP_QUEUE {
                            type uint8;
                        }

                        container STATE {
                            leaf STATUS {
                                type enumeration {
                                    enum Active;
                                    enum Inactive;
                                }
                                description
                                    "Policy bind status Active/Inactive";
                            }

                            leaf MATCHED_PACKETS {
                                type uint64;
                                description
                                    "Number of packets that matched the flow classification criteria";
                            }

                            leaf MATCHED_BYTES {
                                type uint64;
                                description
                                    "Number of bytes that matched the flow classification criteria";
                            }

                            container POLICER {
                                leaf CONFORMED_PACKETS {
                                    type uint64;
                                    description
                                        "matching green packet count for policier counters";
                                }
                                leaf CONFORMED_BYTES {
                                    type uint64;
                                    description
                                        "matching green packet count for policier counters";
                                }
                                leaf EXCEED_PACKETS {
                                    type uint64;
                                    description
                                        "matching yellow packet count for policier counters";
                                }
                                leaf EXCEED_BYTES {
                                    type uint64;
                                    description
                                        "matching yellow packet count for policier counters";
                                }
                                leaf VIOLATED_PACKETS {
                                    type uint64;
                                    description
                                        "matching red packet count for policier counters";
                                }
                                leaf VIOLATED_BYTES {
                                    type uint64;
                                    description
                                        "matching red packet count for policier counters";
                                }
                                leaf CONFORMED_PACKET_ACTION {
                                    type string;
                                    description
                                        "green packet action";
                                }
                                leaf EXCEED_PACKET_ACTION {
                                    type string;
                                    description
                                        "yellow packet action";
                                }
                                leaf VIOLATED_PACKET_ACTION {
                                    type string;
                                    description
                                        "red packet action";
                                }
                                leaf OPERATIONAL_CIR {
                                    type uint64;
                                }
                                leaf OPERATIONAL_CBS {
                                    type uint64;
                                }
                                leaf OPERATIONAL_PIR {
                                    type uint64;
                                }
                                leaf OPERATIONAL_PBS {
                                    type uint64;
                                }
                                leaf UNITS {
                                    type enumeration {
                                        enum BYTES;
                                    }
                                }
                                leaf COLOR_SOURCE {
                                    type enumeration {
                                        enum COLOR-BLIND;
                                    }
                                }
                                leaf STATUS {
                                    type enumeration {
                                        enum Active;
                                        enum Inactive;
                                    }
                                }
                            }

                            container FORWARDING_SELECTED {
                                leaf PACKET_ACTION {
                                    type enumeration {
                                        enum DROP;
                                    }
                                }

                                leaf INTERFACE_NAME {
                                    type string;
                                }

                                leaf IP_ADDRESS {
                                    type string;
                                }

                                leaf VRF {
                                    type string;
                                }

                                leaf PRIORITY {
                                    type uint16;
                                }

                                leaf SET_IP_NEXTHOP_GROUP {
                                    type string;
                                }

                                leaf SET_IPV6_NEXTHOP_GROUP {
                                    type string;
                                }
                            }
                        }
                    }
                }
            }
        }
    }

    rpc clear-service-policy-counters {
        description
            "Clear the countes associated with the policy like Match counters and Policer counters etc.
            Policy name or Interface name is mandatory. The following list shows the different combination supported

            Policy Name only:: Clear counters for all applications of this policy
            Intf Name only:: Clear counters for all policies applied for the interface.
            Type only:: Not supported.
            Policy Name + Intf Name:: Clear counters for specific application of the policy to interface.
            Policy Name + Type:: Same as specifying just policy name but with added validation for type match.
            Intf Name + Type:: Clear counters for specified policy type on the interface.
            Policy Name + Intf Name + Type:: Same as Policy Name + Intf Name but added validation for type match.";

        input {
            leaf POLICY_NAME {
                type string;
                description
                    "Name of the policy to retrieved.";
            }
            leaf INTERFACE_NAME {
                type string;
                description
                    "Interface name on which the policy is applied.";
            }
            leaf TYPE {
                type policy-types;
                description
                    "Type of the policy to retrieved. (Optional)";
            }
        }
    }

    rpc get-pbf-next-hop-group {
        description
            "Get PBF next-hop group information";

        input {
            leaf GROUP_NAME {
                type string;
            }

            leaf TYPE {
                type pbf-next-hop-group-type;
            }
        }
        output {
            list GROUPS {
                key GROUP_NAME;

                leaf GROUP_NAME {
                    type string;
                }

                leaf TYPE {
                    type pbf-next-hop-group-type;
                }

                leaf DESCRIPTION {
                    type string;
                }

                leaf THRESHOLD_TYPE {
                    type enumeration {
                        enum PERCENTAGE;
                        enum COUNT;
                    }
                }

                leaf THRESHOLD_UP {
                    type uint8;
                }

                leaf THRESHOLD_DOWN {
                    type uint8;
                }

                list NEXT_HOPS {
                    key ENTRY_ID;

                    leaf ENTRY_ID {
                        type uint16;
                    }

                    leaf IP_ADDRESS {
                        type string;
                    }

                    leaf VRF {
                        type string;
                    }

                    leaf NEXT_HOP_TYPE {
                        type enumeration {
                            enum non-recursive;
                            enum recursive;
                            enum overlay;
                        }
                    }
                }

                list REFERENCES {
                    leaf POLICY_NAME {
                        type string;
                    }

                    leaf PRIORITY {
                        type uint16;
                    }
                }
            }
        }
    }

    rpc get-pbf-replication-group {
        description
            "Get PBF replication group information";

        input {
            leaf GROUP_NAME {
                type string;
            }

            leaf TYPE {
                type pbf-replication-group-type;
            }
        }
        output {
            list GROUPS {
                key GROUP_NAME;

                leaf GROUP_NAME {
                    type string;
                }

                leaf TYPE {
                    type pbf-replication-group-type;
                }

                leaf DESCRIPTION {
                    type string;
                }

                list NEXT_HOPS {
                    key ENTRY_ID;

                    leaf ENTRY_ID {
                        type uint16;
                    }

                    leaf IP_ADDRESS {
                        type string;
                    }

                    leaf VRF {
                        type string;
                    }

                    leaf NEXT_HOP_TYPE {
                        type enumeration {
                            enum non-recursive;
                            enum recursive;
                            enum overlay;
                        }
                    }

                    leaf SINGLE_COPY {
                        type boolean;
                    }
                }

                list REFERENCES {
                    leaf POLICY_NAME {
                        type string;
                    }

                    leaf PRIORITY {
                        type uint16;
                    }
                }
            }
        }
    }
}
