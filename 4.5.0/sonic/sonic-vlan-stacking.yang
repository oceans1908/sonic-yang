module sonic-vlan-stacking {

    yang-version 1.1;

    namespace "http://github.com/Azure/sonic-vlan-stacking";
    prefix vlan-stacking;

    import sonic-common {
        prefix scommon;
    }

    import sonic-port {
        prefix port;
    }

    import sonic-portchannel {
        prefix lag;
    }

    import sonic-vlan {
        prefix vlan;
    }

    import sonic-extension {
        prefix sonic-ext;
    }

    organization
        "SONiC";

    contact
        "SONiC";

    description "VLAN Stacking YANG Module for SONiC OS";

    revision 2021-12-15 {
        description "First Revision";
    }

    container sonic-vlan-stacking {
        description "Top Level container for VLAN_STACKING";
        container VLAN_STACKING {
            description "VLAN_STACKING part of CONFIG DB";

            list VLAN_STACKING_LIST {

                key "ifname s_vlan stage";
                sonic-ext:custom-validation IsVlanMappingConfigurable;
                description "List of stacking parameters";

                leaf ifname {
                    type union {
                        type leafref {
                            path "/port:sonic-port/port:PORT/port:PORT_LIST/port:ifname";
                        }
                        type leafref {
                            path "/lag:sonic-portchannel/lag:PORTCHANNEL/lag:PORTCHANNEL_LIST/lag:name";
                        }
                    }
                    description "Interface name on which stacking rules are applied";
                }

                leaf s_vlan {
                    sonic-ext:custom-validation ValidateVlanConfig;
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                    description "Service VLAN";
                }

                leaf stage {
                    type scommon:stack_stage;
                    description "Stage(ingress/egress) at which VLAN Translation rule is applied";
                }

                leaf-list c_vlanids {
                    sonic-ext:custom-validation ValidateCvlanL2TPConfig;
                    type union {
                        type uint16 {
                            range "1..4095" {
                                error-message "Vlan ID out of range";
                                error-app-tag vlanid-invalid;
                            }
                        }
                        type string {
                            length 1..10 {
                                error-message "Invalid VLAN Range format";
                                error-app-tag vlan-range-format-invalid;
                            }
                            pattern '(409[0-5]|40[0-8][0-9]|[1-3][0-9]{3}|[1-9][0-9]{2}|[1-9][0-9]|[1-9])-(409[0-5]|40[0-8][0-9]|[1-3][0-9]{3}|[1-9][0-9]{2}|[1-9][0-9]|[1-9])' {
                                error-message "Invalid VLAN Range format";
                                error-app-tag vlan-range-format-invalid;
                            }
                        }
                    }
                    description "Customer VLAN ID";
                    min-elements 1;
                }

                leaf s_vlan_priority {
                    type uint8 {
                         range 0..7 {
                            error-message "Invalid VLAN Priority";
                            error-app-tag vlan-priority-invalid;
                         }
                    }
                    description "VLAN priority of Service VLAN";
               }

            }
        }
    }
}
