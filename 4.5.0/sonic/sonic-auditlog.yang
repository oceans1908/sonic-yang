module sonic-auditlog {
    namespace "http://github.com/Azure/sonic-auditlog";
    prefix auditlog;
    yang-version 1.1;

    organization
        "SONiC";

    contact
        "SONiC";

    description
        "SONiC yang for audit log.";

    revision 2020-05-29 {
        description
            "Initial revision.";
    }

    typedef auditd-system-rules-type {
        description "Auditd system rules type";
        type enumeration {
            enum BASIC {
                description
                "Rules for monitoring sessions and packages update";
            }

            enum DETAIL {
                description
                "Extensive rules for monitoring update
                 in users, groups, kernel modules, audit rules, cron jobs,
                 configuration files, etc. including rules defined in Basic type";
            }

            enum CUSTOM {
                description
                "This mode allows user to configure their custom rules.
                User to copy the custom rules file to config://auditd-custom.rules
                prior to setting CUSTOM.";
            }

            enum NONE {
                description
                "No rules configured";
            }            
        }
    }
    
    container sonic-auditlog {
        container AUDITD_SYSTEM {
            description 
            "Auditd system configuration";
            container global {
                description "Global auditd configuration";
       
                leaf audit-rules  {
                    type auditd-system-rules-type;
                    description "Auditd system rules type";
                }
            }
        }
    }


    rpc get-auditlog {
       description "RPC for getting audit log.";

       input {
           leaf content-type {
               type string {
                   pattern "all";
               }
               description "Indicates if user wants to get all or latest twenty lines of audit log";
           }
       }

       output {
           list audit-content {
               leaf content {
                   type string;
                   description "Audit message";
               }
           }
       }
    }

    rpc clear-auditlog {
       description "RPC for clearing audit log.";

       output {
           leaf status {
               type string;
               description "Clear operation status";
           }
       }
    }
}
