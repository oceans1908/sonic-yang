module openconfig-ospfv2-ext {

  yang-version "1.1";

  // namespace
  namespace "http://openconfig.net/yang/ospfv2/extension";

  prefix "oc-ospfv2-ext";

  // import some basic types
  import ietf-yang-types { prefix "yang"; }
  import ietf-inet-types { prefix "inet"; }
  import openconfig-network-instance { prefix oc-netinst; }
  import openconfig-interfaces { prefix "oc-if"; }
  import openconfig-routing-policy { prefix "oc-rpol"; }
  import openconfig-if-ip { prefix oc-ip; }
  import openconfig-policy-types { prefix "oc-pol-types"; }
  import openconfig-extensions { prefix oc-ext; }
  import openconfig-vlan { prefix oc-vlan; }
  import openconfig-bfd  { prefix oc-bfd; }

  // import ospfv2 module
  import openconfig-ospfv2 { prefix "oc-ospfv2"; }
  import openconfig-ospf-common { prefix "oc-ospf-cmn"; }
  import openconfig-ospf-common-ext { prefix "oc-ospf-ext"; }
  import openconfig-ospf-types { prefix "oc-ospf-types"; }

  organization
    "OCP SONiC Subproject";

  contact
    "OCP SONiC Subproject Working Group";

  description
    "An OpenConfig model for Open Shortest Path First (OSPF)
    version 2 extensions ";

  oc-ext:openconfig-version "0.1.2";

  revision "2024-04-18" {
    description
      "Moved common models to openconfig-ospf-common";
    reference
      "0.1.2";
  }

  revision "2020-03-21" {
    description
      "Add OSPFv2 yang extensions for FRR config and show";
    reference
      "0.1.1";
  }

  identity VIRTUALLINK_NETWORK {
    base "oc-ospf-types:OSPF_NETWORK_TYPE";
    description
      "type of ospf network";
  }

  identity OSPF_CONFIG_TYPE {
    description
      "OSPF Configuration types";
  }

  identity ENABLE {
    base "OSPF_CONFIG_TYPE";
    description
      "Configuration has been enabled";
  }

  identity DISABLE {
    base "OSPF_CONFIG_TYPE";
    description
      "Configuration has been disabled";
  }

  identity DEFAULT {
    base "OSPF_CONFIG_TYPE";
    description
      "Configuration has been set to default";
  }

  identity OSPF_METRIC_TYPE {
    description
      "OSPF Metric Types";
  }

  identity TYPE_1 {
    base "OSPF_METRIC_TYPE";
    description
      "When the metric of a prefix is specified as Type 1
      then it is considered to be expressed in the same units as
      the link-state metrics carried in OSPF. That is to say
      that the metric advertised is directly compared to the
      internal cost";
  }

  identity TYPE_2 {
    base "OSPF_METRIC_TYPE";
    description
      "When the metric of a prefix is specified as Type 2 then
      it is considered to be expressed as a cost in addition to
      that of the link-state metric to the advertising router.
      That is to say that the metric is considered to be the
      cost to the advertising router plus the advertised metric
      for the external entity";
  }

  identity OSPF_POLICY_DIRECTION {
    description
      "OSPF Policy direction";
  }

  identity IMPORT {
    base "OSPF_POLICY_DIRECTION";
    description
      "Policy direction in or import";
  }

  identity EXPORT {
    base "OSPF_POLICY_DIRECTION";
    description
      "Policy direction out or export";
  }

  identity KERNEL {
    base "oc-pol-types:INSTALL_PROTOCOL_TYPE";
    description
      "Policy protocol Kernel Route";
  }

  identity DEFAULT_ROUTE {
    base "oc-pol-types:INSTALL_PROTOCOL_TYPE";
    description
      "Policy default route originate";
  }

  identity OSPF_ROUTER_TYPE {
    description
      "OSPF router type or role";
  }

  identity ABR {
    base "OSPF_ROUTER_TYPE";
    description
      "OSPF router is an ABR";
  }

  identity ASBR {
    base "OSPF_ROUTER_TYPE";
    description
      "OSPF router is an ASBR";
  }

  identity INTERNAL {
    base "OSPF_ROUTER_TYPE";
    description
      "OSPF router is an Internal Router";
  }

  identity BACKBONE {
    base "OSPF_ROUTER_TYPE";
    description
      "OSPF router is an Internal Router";
  }

  identity ABRASBR {
    base "OSPF_ROUTER_TYPE";
    description
      "OSPF router is an ABR and ASBR";
  }

  identity OSPF_ABR_TYPE {
    description
      "OSPF ABR type";
  }

  identity CISCO {
    base "OSPF_ABR_TYPE";
    description
      "CISCO ABR Type";
  }

  identity IBM {
    base "OSPF_ABR_TYPE";
    description
      "IBM ABR Type";
  }

  identity STANDARD {
    base "OSPF_ABR_TYPE";
    description
      "STANDARD ABR Type";
  }

  identity SHORTCUT {
    base "OSPF_ABR_TYPE";
    description
      "SHORTCUT ABR Type";
  }

  identity OSPF_LOG_TYPE {
    description
      "OSPF Metric Types";
  }

  identity LOG_NONE {
    base "OSPF_LOG_TYPE";
    description
      "OSPF Log or show type none";
  }

  identity BRIEF {
    base "OSPF_LOG_TYPE";
    description
      "OSPF Log or show type brief";
  }

  identity DETAIL {
    base "OSPF_LOG_TYPE";
    description
      "OSPF Log or show type detail";
  }

  identity OSPF_NSSA_TRANSLATE_TYPE {
    description
      "OSPF NSSA Translate type";
  }

  identity ALWAYS {
    base "OSPF_NSSA_TRANSLATE_TYPE";
    description
      "OSPF Translate type always";
  }

  identity CANDIDATE {
    base "OSPF_NSSA_TRANSLATE_TYPE";
    description
      "OSPF Translate type candidate election";
  }

  identity NEVER {
    base "OSPF_NSSA_TRANSLATE_TYPE";
    description
      "OSPF Translate type never";
  }

  identity OSPF_ROUTE_TOS {
    description
      "OSPF route Type of Service";
  }

  identity TOS0 {
    base OSPF_ROUTE_TOS;
    description
      "normal service";
  }

  identity OSPF_ROUTE_TABLE {
    description
      "OSPF Route type";
  }

  identity NETWORK_ROUTE_TABLE {
    base "OSPF_ROUTE_TABLE";
    description
      "OSPF network route";
  }

  identity ROUTER_ROUTE_TABLE {
    base "OSPF_ROUTE_TABLE";
    description
      "OSPF router route";
  }

  identity EXTERNAL_ROUTE_TABLE {
    base "OSPF_ROUTE_TABLE";
    description
      "OSPF router route";
  }


  identity OSPF_ROUTE_TYPE {
    description
      "OSPF Route type";
  }

  identity NETWORK_ROUTE {
    base "OSPF_ROUTE_TYPE";
    description
      "OSPF network route";
  }

  identity ROUTER_ROUTE {
    base "OSPF_ROUTE_TYPE";
    description
      "OSPF router route";
  }

  identity EXTERNAL_ROUTE {
    base "OSPF_ROUTE_TYPE";
    description
      "OSPF external route";
  }

  identity OSPF_ROUTE_PATH_TYPE {
    description
      "OSPF Route Path type";
  }

  identity IA_ROUTE {
    base "OSPF_ROUTE_PATH_TYPE";
    description
      "OSPF inter area route";
  }

  identity EXTERNAL_ROUTE_TYPE_1 {
    base "OSPF_ROUTE_PATH_TYPE";
    description
      "OSPF external route type-1";
  }

  identity EXTERNAL_ROUTE_TYPE_2 {
    base "OSPF_ROUTE_PATH_TYPE";
    description
      "OSPF external route type 2";
  }

  grouping ospfv2-ext-global-config {
    description
      "Global configuration for OSPFv2 extended";

    uses oc-ospf-ext:ospf-ext-global-config;

    leaf log-adjacency-state-changes {
      type identityref {
         base "OSPF_LOG_TYPE";
      }
      description
        "Log adjacency state changes";
    }

    leaf ospf-rfc1583-compatible {
      type boolean;
      description
        "OSPF RFC1538 comaptible";
    }
    
    leaf opaque-lsa-capability {
        type boolean;
        description
          "When the value of this leaf is set to true, opaque LSA
          capability (rfc2370) is enabled.";
    }

    leaf passive-interface-default {
      type boolean;
      description
        "OSPF configuration for default passive interface";
    }

    leaf abr-type {
      type identityref {
        base "OSPF_ABR_TYPE";
      }
      description
        "OSPF ABR type";
    }    
  }

  grouping ospfv2-ext-global-state {
    description "OSPFv2 Global state information for ospf enabled router";

    uses oc-ospf-ext:ospf-ext-global-state;

    leaf router-type {
      type identityref {
        base "OSPF_ROUTER_TYPE";
      }
      description
        "OSPF Router type or role (ABR, ASBR)";
    }

    leaf external-lsa-checksum {
      type yang:hex-string;
      description
        "Checksum of external LSA for this ospf enabled router";
    }
    
    leaf stub-advertisement {
      type boolean;
      description
        "stub advertisement flag";
    }
    
    leaf post-start-enabled-secs {
      type uint32 ;
      description
        "post start in seconds";
    }

    leaf opaque-lsa-count {
      type  yang:counter32;
      description
        "Total count of opaque LSA for this ospf enabled router";
    }

    leaf opaque-lsa-checksum {
      type yang:hex-string;
      description
        "Checksum of opaque LSA for this ospf enabled router";
    }

    leaf pre-shutdown-period {
      type uint32;
      units seconds;
      description
        "pre shutdown in seconds";
    }
  }

  grouping ospfv2-ext-area-config {
    description
      "Configuration parameters relating to an OSPF area";

    leaf authentication-type {
      type string;
      description
         "OSPF autentication type";
    }

    leaf shortcut {
      type identityref {
        base "OSPF_CONFIG_TYPE";
      }
      description
         "OSPF area shortcut configuration. Shortcut area setting will 
         take effect only when the router is configured as Shortcut ABR";
    }
  }

  grouping ospfv2-ext-message-digest-authentication-config {
    description
      "Configuration parameters relating to a message digest authentication";

    leaf authentication-key-id {
      type uint8;
      description
        "Message digest key ID";
    }

    leaf authentication-md5-key {
      type string;
      description
        "OSPF authentication password string.";
    }

    leaf authentication-key-encrypted {
      type boolean;
      description
         "OSPF authentication password string is encrypted.";
    }
  }

  grouping ospfv2-ext-message-digest-authentication-top {
    description
      "Configuration parameters relating to a message digest authentication";

    container md-authentications {
      description
        "Configuration and state parameters relating
        message digest authentication";

      list md-authentication {
        key "authentication-key-id";

        description
          "Configuration and state parameters relating
          message digest authentication";

        leaf authentication-key-id {
          type leafref {
            path "../config/authentication-key-id";
          }
          description
            "Authentication key ID";
        }

        container config {
          description
             "Configuration parameters relating to a message digest authentication";
          uses ospfv2-ext-message-digest-authentication-config;
        }

        container state {
          config false;
          description
            "State parameters relating to a message digest authentication";
          uses ospfv2-ext-message-digest-authentication-config;
        }
      }
    }
  }

grouping ospfv2-ext-area-state {
    description
      "Enclosing container for the OSPFv2 area state parameters";

    uses oc-ospf-ext:ospf-ext-area-state;

    leaf interface-count {
      type uint32;
      description
        "Total Number of interfaces in this area";
    }

    leaf active-interface-count {
      type uint32;
      description
        "Total Number of active interfaces in this area";
    }

    leaf adjacency-count {
      type uint32;
      description
        "Total Number of fully adjacent neighbors in this area";
    }    

    leaf spf-execution-count {
      type uint32;
      description
        "Total Number of times spf algorithms executed in this area";
    }

    leaf router-lsa-count {
      type uint32;
      description
        "Total count of router LSA in this area";
    }

    leaf network-lsa-count {
      type uint32;
      description
        "Total count of network LSA in this area";
    }    

    leaf nssa-lsa-count {
      type uint32;
      description
        "Total count of nssa LSA in this area";
    }    

    leaf router-lsa-checksum {
      type yang:hex-string;
      description
        "Router LSA checksum";
    }

    leaf network-lsa-checksum {
      type yang:hex-string;
      description
        "Network LSA checksum";
    }    

    leaf nssa-lsa-checksum {
      type yang:hex-string;
      description
        "NSSA LSA checksum";
    }     

    leaf indefinite-active-admin {
      type boolean;
      description
        "Indefinite active admin";
    }

    leaf virtual-link-adjacency-count {
      type yang:counter32;
      description
        "Total Number of virtual link adjacent neighbors in this area";
    }

    leaf summary-lsa-count {
      type yang:counter32;
      description
        "Total count of summary LSA in this area";
    }

    leaf asbr-summary-lsa-count {
      type yang:counter32;
      description
        "Total count of asbr summary LSA in this area";
    }

    leaf opaque-link-lsa-count {
      type yang:counter32;
      description
        "Total count of opaque link LSA in this area";
    }

    leaf opaque-area-lsa-count {
      type yang:counter32;
      description
        "Total count of opaque area LSA in this area";
    }

    leaf summary-lsa-checksum {
      type yang:hex-string;
      description
        "Summary LSA checksum";
    }

    leaf asbr-summary-lsa-checksum {
      type yang:hex-string;
      description
        "ASBR summary LSA checksum";
    }

    leaf opaque-link-lsa-checksum {
      type yang:hex-string;
      description
        "Opaque link LSA checksum";
    }

    leaf opaque-area-lsa-checksum {
      type yang:hex-string;
      description
        "Opaque area LSA checksum";
    }    

    leaf origin-stub-max-dist-router-lsa {
      type boolean;
      description
        "max metric router LSA";
    }
}

grouping ospfv2-ext-policy-route-distribute-list-config {
    description
      "Configuration parameters relating to route distribution.
       This policy configuration includes both route import and
       route exports. Protocols can be BGP, CONNECTED, KERNEL,
       STATIC and DEFAULT routes.";

    leaf protocol {
      type identityref {
        base "oc-pol-types:INSTALL_PROTOCOL_TYPE";
      }
      description
        "Access-list map name for filter prefixes";
    }

    leaf direction {
      type identityref {
        base "OSPF_POLICY_DIRECTION";
      }
      description
        "Access-list name for filter prefixes";
    }

    leaf description {
       type string;
       default "OSPF Route distribution list";
       description
         "String description for the configured Route distribution list";
    }

    leaf table-id {
      when "../direction = 'IMPORT' and ../protocol = 'OSPF'";
      type uint32;
      default 0;
      description
        "OSPF instance id for route distribution";
    }

    leaf always {
      when "../direction = 'IMPORT' and ../protocol = 'DEFAULT_ROUTE'";
      type boolean;
      description
         "Always distribute default route";
    }

    leaf metric {
      when "../direction = 'IMPORT'";
      type oc-ospf-ext:ospf-cost-metric;
      description
        "OSPF metric for route distribution";
    }

    leaf metric-type {
      when "../direction = 'IMPORT'";
      type identityref {
        base "OSPF_METRIC_TYPE";
      }
      description
        "OSPF metrics type for route distribution";
    }

    leaf route-map {
      when "../direction = 'IMPORT'";
      type leafref {
        path "/oc-rpol:routing-policy/oc-rpol:policy-definitions" +
             "/oc-rpol:policy-definition/oc-rpol:name";
      }
      description
        "Route map name for route distribution";
    }
  }

  grouping ospfv2-ext-policy-route-distibute-list-top {
    description
      "Configuration parameters relating to a route distibute list";

    list distribute-list {
      key "protocol direction";

      description
        "Configuration and state parameters relating to a distibute list";

      leaf protocol {
        type leafref {
          path "../config/protocol";
        }
        description
          "Reference to the distribute protocol type";
      }

      leaf direction {
        type leafref {
          path "../config/direction";
        }
        description
          "Reference to the distribute direction";
      }

      container config {
        description
          "Configuration parameters relating to the OSPF distibute list";
        uses ospfv2-ext-policy-route-distribute-list-config;
      }

      container state {
        config false;
        description
          "State parameters relating to the OSPF distibute list";
        uses ospfv2-ext-policy-route-distribute-list-config;
      }
    }
  }

  grouping ospfv2-ext-policy-route-distibution-top {
    description
      "Configuration parameters relating to a route distibute list";

    container route-distribution-policies {
      description
        "Configuration and state parameters relating route distibution";

      uses ospfv2-ext-policy-route-distibute-list-top;
    }
  }

  grouping ospfv2-ext-route-tables-route-state {
    description
      "Operational state parameters relating to an OSPFV2 route";

    leaf prefix {
      type inet:ip-prefix;
      description
        "IPv4 route prefix";
    }

    leaf type {
      type identityref {
         base "OSPF_ROUTE_TYPE";
      }
      description
        "OSPF Route type - Network, Router, external";
    }

    leaf sub-type {
      type identityref {
         base "OSPF_ROUTE_PATH_TYPE";
      }
      description
        "OSPF Route subtype - Inter Area, External Type 1 or 2";
    }


    leaf cost {
      type oc-ospf-ext:ospf-cost-metric;
      description
        "The metric/cost for the route";
    }

    leaf type2-cost {
      type oc-ospf-ext:ospf-cost-metric;
      description
        "The metric/cost for the external route Type 2";
    }

    leaf inter-area {
      type boolean;
      description
        "Inter area route";
    }

    leaf router-type {
      type identityref {
         base "OSPF_ROUTER_TYPE";
      }
      description
        "OSPF Router Type (ABR, ASBR etc)";
    }
  }

  grouping ospfv2-ext-route-tables-route-next-hops-state {
    description
      "Operational state parameters relating to an OSPF route next hops";

    container next-hops {
      description
        "list of nexthops";

      list next-hop {
        key "address out-interface area-id";

        leaf address {
          type leafref {
            path "../state/address";
          }
          description
            "Next hop address";
        }

        leaf out-interface {
          type leafref {
            path "../state/out-interface";
          }
          description
            "outgoing interface name";
        }

        leaf area-id {
          type leafref {
            path "../state/area-id";
          }
          description
            "area-id of the outgoing interface";
        }

        description
          "List of OSPF nexthops with ecmp legs";
        container state {
          description
            "state information for a single nexthop";
          leaf address {
            type inet:ip-address;
            description
              "Next hop address";
          }

          leaf out-interface {
            type string;
            description
              "Outgoing interface name";
          }

          leaf area-id {
            type yang:dotted-quad;
            description
              "Route area id";
          }
        }
      }
    }
  }

  grouping ospfv2-ext-route-tables-routes-state {
    description
      "Enclosing container for the list of OSPF routes";

    container routes {
      description
        "state information for route-table-state";

      list route {
        key "prefix";
        leaf prefix {
          type leafref {
            path "../state/prefix";
          }
          description
            "Reference to the prefix address in the route table";
        }

        description
          "List of OSPF routes";

        container state {
          config false;
          description
            "state information for a single route";

          uses ospfv2-ext-route-tables-route-state;
        }

        uses ospfv2-ext-route-tables-route-next-hops-state;
      }
    }
  }

  grouping ospfv2-ext-route-tables-state {
    description
      "Enclosing container for the list of OSPF routes";

    container route-tables {
      config false;
      description
        "Enclosing container for the list of OSPF routes";

      list route-table {
        key "type";

        description
          "different type of route table e.g. router or network or external table";
        leaf type {
          type leafref {
            path "../state/type";
          }
            description
              "Reference to the different type of route table e.g. router or network or external table";
        }
        container state {
          description
            "state information for different type of route table e.g. router or network or external table";

          leaf type {
            type identityref {
              base "OSPF_ROUTE_TABLE";
            }
            description
              "OSPF Route table type";
          }
        }

        uses ospfv2-ext-route-tables-routes-state;
      }
    }
  }

  grouping ospfv2-ext-area-virtual-link-state {
    description
      "State parameters for an OSPF Virtual Link interface";

    leaf name {
      type string;
      description
        "Name of the virtual link";
    }

    leaf area-id {
      type oc-ospf-types:ospf-area-identifier;
      description
        "The area which the vlink belongs to.";
    }

    leaf network-type {
      type identityref {
        base "oc-ospf-types:OSPF_NETWORK_TYPE";
      }
      description
        "The type of network that OSPF should use for the specified
        interface.";
    }

    leaf mtu-ignore {
      type boolean;
      description
         "OSPF interface MTU ignore configuration.";
    }

    leaf index {
      type uint32;
      description
        "Interface index";
    }

    leaf bandwidth {
      type uint32;
      description
        "Interface bandwidth in Megabits";
    }

    leaf operational-state {
      type string;
      description
        "Interface combined operational state(e.g. up/down)";
    }

    leaf status {
      type string;
      description
        "This states the functional state like DR, point to point etc";
    }

    leaf if-flags {
      type string;
      description
        "Interface Flag indicating support for multicast, status etc";
    }

    leaf address {
      type inet:ipv4-address-no-zone;
      description
        "local address of the vlink";
    }

    leaf peer-address {
      type inet:ipv4-address-no-zone;
      description
        "Address used to reach the peer";
    }

    leaf broadcast-address {
      type inet:ipv4-address-no-zone;
      description
        "Broadcast address address";
    }

    leaf mtu {
      type uint32;
      description
        "Interface MTU";
    }

    uses oc-ospf-ext:ospf-ext-router-id;

    leaf adjacency-status {
      type string;
      description
        "The state of the adjacency with the neighbor,
        or it can also indicate state like DR/BDR.";
    }

    leaf backup-designated-router-address {
      type inet:ipv4-address-no-zone;
      description
        "Backup Designated router address";
    }

    leaf designated-router-other {
      type yang:dotted-quad;
      description
        "DR Other router";
    }

    leaf  member-of-ospf-all-routers {
      type boolean;
      description
        "Member of OSPF All router multicast group";
    }

    leaf member-of-ospf-designated-routers {
      type boolean;
      description
        "Member of OSPF Designated router multicast group";
    }

    leaf neighbor-count {
      type uint32;
      description
        "Neighbor count";
    }

    leaf adjacency-count {
      type uint32;
      description
        "Adjacency count";
    }

    leaf bfd-state {
      type boolean;
      description
        "BFD State";
    }

    leaf ospf-enable {
      type boolean;
      description
        "Ospf Enable State";
    }

    leaf address-len {
      type uint8;
      description
        "Prefix length of the ip address configured on the interface";
    }

    leaf ospf-interface-type {
      type string;
      description
        "Type of OSPF interface like point-to-point, broadcast etc";
    }

    leaf cost {
      type uint32;
      description
        "Metric for this interface";
    }

    leaf network-lsa-sequence-number {
      type yang:hex-string;
      description
        "Saved Network-LSA sequence number in hex";
    }
  }

  grouping ospfv2-ext-area-nssa-config {
    description
      "Area NSSA configuration for OSPF";

    leaf enable {
      type boolean;
      description
         "OSPF area NSSA configuration.";
    }

    leaf no-summary {
      type boolean;
      description
        "OSPF area NSSA no summary configuration.";
    }

    leaf translate {
      type identityref {
        base "OSPF_NSSA_TRANSLATE_TYPE";
      }
      default CANDIDATE;
      description
        "OSPF area NSSA translate type configuration.";
    }
  }

  grouping ospfv2-ext-area-nssa-top {
    description
      "Area NSSA configuration for OSPF";

    container nssa {
      description
        "Area NSSA configuration for OSPF";

      container config {
        description
          "Config for Area NSSA configuration for OSPF";
        uses ospfv2-ext-area-nssa-config;
      }

      container state {
        config false;
        description
          "State for Area NSSA for OSPF";
        uses ospfv2-ext-area-nssa-config;
      }
    }
  }

  grouping ospfv2-ext-policy-default-route-originate-config {
    description
      "Distribute a default route configuration for OSPF
      Originate an AS-External (type-5) LSA describing a default
      route into all external-routing capable areas, of the
      specified metric and metric type. If the 'always' field is
      enabled then the default is always advertised, even when
      there is no default present in the routing table.";

    leaf always {
      type boolean;
      description
         "Always advertise default route";
    }

    leaf metric {
      type oc-ospf-ext:ospf-cost-metric;
      description
        "OSPF default route metric.";
    }

    leaf metric-type {
      type identityref {
        base "OSPF_METRIC_TYPE";
      }
      description
        "OSPF External Type 1/2 metrics";
    }

    leaf route-map {
      type leafref {
        path "/oc-rpol:routing-policy/oc-rpol:policy-definitions" +
             "/oc-rpol:policy-definition/oc-rpol:name";
      }
      description
        "Distribute a default route using Route map";
    }
  }

  grouping ospfv2-ext-lsdb-router-lsa-link-info-state {
    description
      "Describes the router lsa information";

    leaf type {
      type identityref {
        base "oc-ospf-types:ROUTER_LSA_TYPES";
      }
      description
        "The sub-type of the Router LSA.";
    }

    leaf metric {
      type oc-ospf-types:ospf-metric;
      description
      "The cost of utilising the link specified independent of TOS";
    }

    leaf number-tos-metrics {
      type uint16;
      description
        "The number of different TOS metrics given for this link, not
        including the link metric (which is referred to as TOS 0).";
    }

    uses oc-ospfv2:ospfv2-lsdb-common-link-specification;
  }

  grouping ospfv2-ext-lsdb-router-lsa-link-informations-state {
    description
      "Parameters related to router LSA Link information list";

    container link-informations {
      config false;
      description
        "Enclosing container for the list of links present in the router LSA";

      list link-information {
        description
          "Describes the links present in the router LSA (e.g. point-to-point, transit etc)";

        container state {
          config false;
          description
            "State parameters relating to the OSPF passive interface";

          uses ospfv2-ext-lsdb-router-lsa-link-info-state;
        }
      }
    }
  }

  grouping ospfv2-ext-lsdb-router-lsa-structure-state {
    description
      "Structural grouping for Router LSA contents within the LSDB";

    container router-lsa {
      config false;
      description
        "Contents of the router LSA";

      container state {
        description
          "State parameters of the router LSA";
        uses oc-ospf-ext:ospf-ext-lsdb-router-lsa-state;
      }

      uses ospfv2-ext-lsdb-router-lsa-link-informations-state;
      uses oc-ospf-cmn:ospf-lsdb-generic-lsa-tos-metric-structure;
    }
  }

  grouping ospfv2-ext-area-lsdb-lsa-state {
    description
      "OSPF area lsdb lsa state information";

    list lsa-ext {
      key "link-state-id advertising-router";

      description
        "List of the LSAs of a specified type in the
        LSDB for the specified area";

      leaf link-state-id {
        type leafref {
          path "../state/link-state-id";
        }
        description
          "Reference to the Link State ID of the LSA";
      }

      leaf advertising-router {
        type leafref {
          path "../state/advertising-router";
        }
        description
          "Reference to the advertising-router of the LSA";
      }

      container state {
        description
          "Operational state parameters relating to all
          LSA types";
        uses oc-ospfv2:ospfv2-lsdb-area-lsa-state;
        uses oc-ospf-ext:ospf-ext-lsdb-area-lsa-state;
      }

      uses ospfv2-ext-lsdb-router-lsa-structure-state {
        when "../../oc-netinst:state/oc-netinst:type = 'ROUTER_LSA'" {
          description
            "Include the router LSA hierarchy solely when
            that LSA type is being described";
        }
      }

      uses oc-ospf-cmn:ospf-lsdb-network-lsa-structure {
        when "../../oc-netinst:state/oc-netinst:type = 'NETWORK_LSA'" {
          description
            "Include the network LSA hierarchy solely when
            that LSA type is being described";
        }
      }

      uses oc-ospfv2:ospfv2-lsdb-summary-lsa-structure {
        when "../../oc-netinst:state/oc-netinst:type = " +
          "'SUMMARY_IP_NETWORK_LSA' or " +
          "../../oc-netinst:state/oc-netinst:type = 'SUMMARY_ASBR_LSA'" {
          description
            "Include the summary LSA hierarchy solely when
            that LSA type is being described";
        }
      }

      uses oc-ospf-cmn:ospf-lsdb-asexternal-lsa-structure {
        when "../../oc-netinst:state/oc-netinst:type = 'AS_EXTERNAL_LSA'" {
          description
            "Include the AS external LSA hierarchy solely when
            that LSA type is being described";
        }
      }

      uses oc-ospf-cmn:ospf-lsdb-nssa-external-lsa-structure {
        when "../../oc-netinst:state/oc-netinst:type = 'NSSA_AS_EXTERNAL_LSA'" {
          description
            "Include the NSSA External LSA hierarchy solely
            when that LSA type is being described";
        }
      }

      uses oc-ospfv2:ospfv2-lsdb-opaque-lsa-structure {
        when "../../oc-netinst:state/oc-netinst:type = 'OSPFV2_LINK_SCOPE_OPAQUE_LSA'
          or ../../oc-netinst:state/oc-netinst:type = 'OSPFV2_AREA_SCOPE_OPAQUE_LSA'
          or ../../oc-netinst:state/oc-netinst:type = 'OSPFV2_AS_SCOPE_OPAQUE_LSA'" {
          description
            "Include the Opaque LSA structure when type of entry
            being described in an opaque LSA";
          }
      }
    }
  }

grouping ospfv2-ext-area-interface-config {
    description
      "Enclosing container for the OSPFv2 area interface configurations";

    uses oc-ospf-ext:ospf-ext-area-interface-config;
    leaf authentication-key {
      type string;
      description
        "OSPF authentication password string.";
    }

    leaf authentication-key-encrypted {
      type boolean;
      description
         "OSPF authentication password string is encrypted.";
    }
}
  
grouping ospfv2-ext-interface-phys-config {
    description
      "Enclosing container for the OSPF configurations";

    container ospfv2 {
      description
        "Enclosing container for the OSPF configurations";

        list if-addresses {
          key "address";

          description
            "Configuration and state parameters relating OSPF interfaces";

          leaf address {
            type leafref {
              path "../config/address";
            }
            description
              "Reference to the passive interface";
          }

          container config {
            description
              "Configuration parameters relating OSPF interfaces";
            uses oc-ospfv2:ospfv2-area-interface-config;
            uses ospfv2-ext-area-interface-config;
            uses oc-ospf-cmn:ospf-area-interface-timers-config;
            uses oc-ospf-ext:ospf-ext-area-interface-timers-config;

          }

          container state {
            config false;
            description
              "State parameters relating OSPF interfaces";
            uses oc-ospfv2:ospfv2-area-interface-config;
            uses ospfv2-ext-area-interface-config;
            uses oc-ospf-cmn:ospf-area-interface-timers-config;
            uses oc-ospf-ext:ospf-ext-area-interface-timers-config;
         }

         uses ospfv2-ext-message-digest-authentication-top;
         uses oc-bfd:bfd-enable;
       }
    }
  }
  deviation "/oc-netinst:network-instances/oc-netinst:network-instance" +
            "/oc-netinst:protocols/oc-netinst:protocol/oc-netinst:ospfv2" +
            "/oc-netinst:global/oc-netinst:config" +
            "/oc-netinst:summary-route-cost-mode" {
    deviate not-supported;
  }

  deviation "/oc-netinst:network-instances/oc-netinst:network-instance" +
            "/oc-netinst:protocols/oc-netinst:protocol/oc-netinst:ospfv2" +
            "/oc-netinst:global/oc-netinst:state" +
            "/oc-netinst:summary-route-cost-mode" {
    deviate not-supported;
  }


  deviation "/oc-netinst:network-instances/oc-netinst:network-instance" +
            "/oc-netinst:protocols/oc-netinst:protocol/oc-netinst:ospfv2" +
            "/oc-netinst:global/oc-netinst:config" +
            "/oc-netinst:igp-shortcuts" {
    deviate not-supported;
  }

  deviation "/oc-netinst:network-instances/oc-netinst:network-instance" +
            "/oc-netinst:protocols/oc-netinst:protocol/oc-netinst:ospfv2" +
            "/oc-netinst:global/oc-netinst:state" +
            "/oc-netinst:igp-shortcuts" {
    deviate not-supported;
  }

  deviation "/oc-netinst:network-instances/oc-netinst:network-instance" +
            "/oc-netinst:protocols/oc-netinst:protocol/oc-netinst:ospfv2" +
            "/oc-netinst:global/oc-netinst:config" +
            "/oc-netinst:hide-transit-only-networks" {
    deviate not-supported;
  }

  deviation "/oc-netinst:network-instances/oc-netinst:network-instance" +
            "/oc-netinst:protocols/oc-netinst:protocol/oc-netinst:ospfv2" +
            "/oc-netinst:global/oc-netinst:state" +
            "/oc-netinst:hide-transit-only-networks" {
    deviate not-supported;
  }

  deviation "/oc-netinst:network-instances/oc-netinst:network-instance" +
            "/oc-netinst:protocols/oc-netinst:protocol/oc-netinst:ospfv2" +
            "/oc-netinst:global/oc-netinst:config" +
            "/oc-netinst:log-adjacency-changes" {
    deviate not-supported;
  }

  deviation "/oc-netinst:network-instances/oc-netinst:network-instance" +
            "/oc-netinst:protocols/oc-netinst:protocol/oc-netinst:ospfv2" +
            "/oc-netinst:global/oc-netinst:state" +
            "/oc-netinst:log-adjacency-changes" {
    deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:config" +
          "/oc-netinst:set" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:config" +
          "/oc-netinst:timeout" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:config" +
          "/oc-netinst:include" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:config" +
          "/oc-netinst:trigger" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:state" +
          "/oc-netinst:set" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:state" +
          "/oc-netinst:timeout" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:state" +
          "/oc-netinst:include" {
        deviate not-supported;
  }

  deviation "/oc-netinst:network-instances/oc-netinst:network-instance" +
          "/oc-netinst:protocols/oc-netinst:protocol/oc-netinst:ospfv2" +
          "/oc-netinst:global/oc-netinst:timers" +
          "/oc-netinst:max-metric/oc-netinst:state" +
          "/oc-netinst:trigger" {
        deviate not-supported;
  }

  deviation "/oc-netinst:network-instances/oc-netinst:network-instance" +
          "/oc-netinst:protocols/oc-netinst:protocol/oc-netinst:ospfv2" +
          "/oc-netinst:global/oc-netinst:timers/oc-netinst:lsa-generation" +
          "/oc-netinst:config/oc-netinst:initial-delay" {
    deviate not-supported;
  }

  deviation "/oc-netinst:network-instances/oc-netinst:network-instance" +
          "/oc-netinst:protocols/oc-netinst:protocol/oc-netinst:ospfv2" +
          "/oc-netinst:global/oc-netinst:timers/oc-netinst:lsa-generation" +
          "/oc-netinst:config/oc-netinst:maximum-delay" {
    deviate not-supported;
  }

  deviation "/oc-netinst:network-instances/oc-netinst:network-instance" +
          "/oc-netinst:protocols/oc-netinst:protocol/oc-netinst:ospfv2" +
          "/oc-netinst:global/oc-netinst:timers/oc-netinst:lsa-generation" +
          "/oc-netinst:state/oc-netinst:initial-delay" {
    deviate not-supported;
  }

  deviation "/oc-netinst:network-instances/oc-netinst:network-instance" +
          "/oc-netinst:protocols/oc-netinst:protocol/oc-netinst:ospfv2" +
          "/oc-netinst:global/oc-netinst:timers/oc-netinst:lsa-generation" +
          "/oc-netinst:state/oc-netinst:maximum-delay" {
    deviate not-supported;
  }

  deviation "/oc-netinst:network-instances/oc-netinst:network-instance" +
          "/oc-netinst:protocols/oc-netinst:protocol/oc-netinst:ospfv2" +
          "/oc-netinst:global/oc-netinst:timers/oc-netinst:lsa-generation" +
          "/oc-netinst:state/oc-netinst:timer-type" {
    deviate not-supported;
  }
  
  deviation "/oc-netinst:network-instances/oc-netinst:network-instance" +
          "/oc-netinst:protocols/oc-netinst:protocol/oc-netinst:ospfv2" +
          "/oc-netinst:global/oc-netinst:timers/oc-netinst:spf" +
          "/oc-netinst:state/oc-netinst:timer-type" {
    deviate not-supported;
  }

  /*
  deviation "/oc-netinst:network-instances/oc-netinst:network-instance" +
          "/oc-netinst:protocols/oc-netinst:protocol/oc-netinst:ospfv2" +
          "/oc-netinst:global/oc-netinst:graceful-restart" {
    deviate not-supported;
  }
  */

  augment "/oc-netinst:network-instances/oc-netinst:network-instance" +
          "/oc-netinst:protocols/oc-netinst:protocol/oc-netinst:ospfv2" +
          "/oc-netinst:global/oc-netinst:graceful-restart" +
          "/oc-netinst:config" {
    description
      "extra parameters related to ospfv2 gracefule restart";
    uses oc-ospf-ext:ospf-ext-global-graceful-restart-config;
    uses oc-ospf-ext:ospf-ext-global-graceful-restart-helper-config;     
  }

  augment "/oc-netinst:network-instances/oc-netinst:network-instance" +
          "/oc-netinst:protocols/oc-netinst:protocol/oc-netinst:ospfv2" +
          "/oc-netinst:global/oc-netinst:graceful-restart" +
          "/oc-netinst:state" {
    description
      "Extra parameters related to ospfv2 gracefule restart";
    uses oc-ospf-ext:ospf-ext-global-graceful-restart-config;
    uses oc-ospf-ext:ospf-ext-global-graceful-restart-status;
    uses oc-ospf-ext:ospf-ext-global-graceful-restart-helper-config;     
    uses oc-ospf-ext:ospf-ext-global-graceful-restart-helper-status;     
  }

  augment "/oc-netinst:network-instances/oc-netinst:network-instance" +
          "/oc-netinst:protocols/oc-netinst:protocol/oc-netinst:ospfv2" +
          "/oc-netinst:global/oc-netinst:graceful-restart" {
    description
      "Extra parameters related to ospfv2 gracefule restart helpers";
    uses oc-ospf-ext:ospf-ext-global-graceful-restart-helpers-neighbor-config;     
  }

  deviation "/oc-netinst:network-instances/oc-netinst:network-instance" +
          "/oc-netinst:protocols/oc-netinst:protocol/oc-netinst:ospfv2" +
          "/oc-netinst:global/oc-netinst:mpls" {
    deviate not-supported;
  }

  deviation "/oc-netinst:network-instances/oc-netinst:network-instance" +
          "/oc-netinst:protocols/oc-netinst:protocol/oc-netinst:ospfv2" +
          "/oc-netinst:global/oc-netinst:inter-area-propagation-policies" +
          "/oc-netinst:inter-area-propagation-policy" {
    deviate not-supported;
  }

  deviation "/oc-netinst:network-instances/oc-netinst:network-instance" +
          "/oc-netinst:protocols/oc-netinst:protocol/oc-netinst:ospfv2" +
          "/oc-netinst:areas/oc-netinst:area/oc-netinst:mpls" {
    deviate not-supported;
  }

  deviation "/oc-netinst:network-instances/oc-netinst:network-instance" +
          "/oc-netinst:protocols/oc-netinst:protocol/oc-netinst:ospfv2" +
          "/oc-netinst:global/oc-netinst:state" +
          "/oc-ospfv2-ext:pre-shutdown-period" {
    deviate not-supported;
  }

  augment "/oc-netinst:network-instances/oc-netinst:network-instance" +
          "/oc-netinst:protocols/oc-netinst:protocol/oc-netinst:ospfv2" +
          "/oc-netinst:global/oc-netinst:config" {
    description
      "extra parameters related to ospfv2 global config";
    uses ospfv2-ext-global-config;
  }

  augment "/oc-netinst:network-instances/oc-netinst:network-instance" +
          "/oc-netinst:protocols/oc-netinst:protocol/oc-netinst:ospfv2" +
          "/oc-netinst:global/oc-netinst:state" {
    description
      "extra parameters related to ospfv2 global state";
    uses ospfv2-ext-global-config;
    uses ospfv2-ext-global-state;
  }

  augment "/oc-netinst:network-instances/oc-netinst:network-instance" +
          "/oc-netinst:protocols/oc-netinst:protocol/oc-netinst:ospfv2" +
          "/oc-netinst:global/oc-netinst:timers/oc-netinst:spf" +
          "/oc-netinst:config" {
    description
      "extra parameters related to ospfv2 global spf timers config";
    uses oc-ospf-ext:ospf-ext-global-timers-spf-config;
  }

  augment "/oc-netinst:network-instances/oc-netinst:network-instance" +
          "/oc-netinst:protocols/oc-netinst:protocol/oc-netinst:ospfv2" +
          "/oc-netinst:global/oc-netinst:timers/oc-netinst:spf" +
          "/oc-netinst:state" {
    description
      "extra parameters related to ospfv2 global spf timers state";
    uses oc-ospf-ext:ospf-ext-global-timers-spf-config;
    uses oc-ospf-ext:ospf-ext-global-timers-spf-state;
  }

  augment "/oc-netinst:network-instances/oc-netinst:network-instance" +
          "/oc-netinst:protocols/oc-netinst:protocol/oc-netinst:ospfv2" +
          "/oc-netinst:global/oc-netinst:timers" +
          "/oc-netinst:max-metric/oc-netinst:config" {
    description
      "extra parameters related to ospfv2 global max metric timers config";
        uses oc-ospf-ext:ospf-ext-global-max-metric-router-lsa-config;
  }

  augment "/oc-netinst:network-instances/oc-netinst:network-instance" +
          "/oc-netinst:protocols/oc-netinst:protocol/oc-netinst:ospfv2" +
          "/oc-netinst:global/oc-netinst:timers" +
          "/oc-netinst:max-metric/oc-netinst:state" {
    description
      "extra parameters related to ospfv2 global max metric timers state";
        uses oc-ospf-ext:ospf-ext-global-max-metric-router-lsa-config;
  }

  augment "/oc-netinst:network-instances/oc-netinst:network-instance" +
          "/oc-netinst:protocols/oc-netinst:protocol/oc-netinst:ospfv2" +
          "/oc-netinst:global/oc-netinst:timers" +
          "/oc-netinst:lsa-generation/oc-netinst:config" {
    description
      "extra parameters related to ospfv2 global lsa-generation timers config";
    uses oc-ospf-ext:ospf-ext-global-lsa-generation-timers-config;
  }

  augment "/oc-netinst:network-instances/oc-netinst:network-instance" +
          "/oc-netinst:protocols/oc-netinst:protocol/oc-netinst:ospfv2" +
          "/oc-netinst:global/oc-netinst:timers" +
          "/oc-netinst:lsa-generation/oc-netinst:state" {
    description
      "extra parameters related to ospfv2 global lsa-generation timers state";
    uses oc-ospf-ext:ospf-ext-global-lsa-generation-timers-config;
  }


  augment "/oc-netinst:network-instances/oc-netinst:network-instance" +
          "/oc-netinst:protocols/oc-netinst:protocol/oc-netinst:ospfv2" +
          "/oc-netinst:global/oc-netinst:inter-area-propagation-policies" {
    description
      "extra parameters related to ospfv2 global inter-area-propagation-policies";
    uses oc-ospf-ext:ospf-ext-inter-area-propagation-policy-top;
  }

  augment "/oc-netinst:network-instances/oc-netinst:network-instance" +
          "/oc-netinst:protocols/oc-netinst:protocol/oc-netinst:ospfv2" +
          "/oc-netinst:global" {
    description
      "extra parameters related to ospfv2 global route distribution policy and passive interface";
    uses ospfv2-ext-policy-route-distibution-top;
    uses oc-ospf-ext:ospf-ext-policy-distance-top;
    uses oc-ospf-ext:ospf-ext-passive-interfaces-top;
  }

  augment "/oc-netinst:network-instances/oc-netinst:network-instance" +
          "/oc-netinst:protocols/oc-netinst:protocol/oc-netinst:ospfv2" +
          "/oc-netinst:areas/oc-netinst:area/oc-netinst:config" {
    description
      "extra parameters related to ospfv2 areas area config";
    uses ospfv2-ext-area-config;
  }

  augment "/oc-netinst:network-instances/oc-netinst:network-instance" +
          "/oc-netinst:protocols/oc-netinst:protocol/oc-netinst:ospfv2" +
          "/oc-netinst:areas/oc-netinst:area/oc-netinst:state" {
    description
      "extra parameters related to ospfv2 areas area state";
    uses ospfv2-ext-area-config;
    uses ospfv2-ext-area-state;
  }

  augment "/oc-netinst:network-instances/oc-netinst:network-instance" +
          "/oc-netinst:protocols/oc-netinst:protocol/oc-netinst:ospfv2" +
          "/oc-netinst:areas/oc-netinst:area" {
    description
      "extra parameters related to ospfv2 areas area stub and network";
    uses oc-ospf-ext:ospf-ext-area-stub-top;
    uses oc-ospf-ext:ospf-ext-area-networks-top;
  }

  augment "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:config" {
    description
      "extra parameters related to ospfv2 areas area virtual-links virtual-link config";
    uses oc-ospf-ext:ospf-ext-area-virtual-link-config;
  }

  augment "/oc-netinst:network-instances/oc-netinst:network-instance" +
          "/oc-netinst:protocols/oc-netinst:protocol/oc-netinst:ospfv2" +
          "/oc-netinst:areas/oc-netinst:area/oc-netinst:virtual-links" +
          "/oc-netinst:virtual-link" {
    description
      "extra parameters related to ospfv2 areas area virtual-links virtual-link config";
    uses ospfv2-ext-message-digest-authentication-top;
    uses oc-ospf-ext:ospf-ext-area-interface-message-stats-top;
    uses oc-ospf-ext:ospf-ext-area-interface-neighbors-state;
  }

  augment "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" {
    description
      "extra parameters related to ospfv2 areas area virtual-links virtual-link state";
    uses oc-ospf-ext:ospf-ext-area-virtual-link-config;
    uses ospfv2-ext-area-virtual-link-state;
    uses oc-ospf-ext:ospf-ext-area-interface-timers-state;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:broadcast-address" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:adjacency-status" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:mtu-ignore" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:bfd-state" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:backup-designated-router-address" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:designated-router-other" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:member-of-ospf-all-routers" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:member-of-ospf-designated-routers" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-ospfv2-ext:network-lsa-sequence-number" {
    deviate not-supported;
  }
  /* Dead timer due is supported on virtual-link neighbors */
  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:dead-time" {
    deviate not-supported;
  }

  /* The below fields will be filled in neighbor detail commands for virtual-links */
  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:designated-router" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:backup-designated-router" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:optional-capabilities" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:last-established-time" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:adjacency-state" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:state-changes" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-netinst:state" +
          "/oc-netinst:retranmission-queue-length" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:bfd-state" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:bfd-status" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:bfd-peer-type" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:bfd-peer-last-update-time" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-active-helper" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-helper-status" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-grace-interval" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-restart-reason" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-helper-reject-reason" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-helper-exit-reason" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-actual-grace-interval" {
    deviate not-supported;
  }

  deviation "/oc-netinst:network-instances/oc-netinst:network-instance" +
          "/oc-netinst:protocols/oc-netinst:protocol/oc-netinst:ospfv2" +
          "/oc-netinst:areas/oc-netinst:area/oc-netinst:virtual-links" +
          "/oc-netinst:virtual-link/oc-ospfv2-ext:neighbours" +
          "/oc-ospfv2-ext:neighbour/oc-ospfv2-ext:state/oc-ospfv2-ext:gr-remaining-grace-interval" {
    deviate not-supported;
  }

  /* SONIC-83272: Mark as not-supported attributes related to OSPF opaque-lsa and NSSA-lsa in yang lsdb: Start */
  deviation "/oc-netinst:network-instances/oc-netinst:network-instance/oc-netinst:protocols" +
            "/oc-netinst:protocol/oc-netinst:ospfv2/oc-netinst:areas/oc-netinst:area/oc-netinst:lsdb" +
            "/oc-netinst:lsa-types/oc-netinst:lsa-type/oc-netinst:lsas/oc-ospfv2-ext:lsa-ext" +
            "/oc-ospfv2-ext:opaque-lsa/oc-ospfv2-ext:state" {
            deviate not-supported;
  }
  deviation "/oc-netinst:network-instances/oc-netinst:network-instance/oc-netinst:protocols" +
            "/oc-netinst:protocol/oc-netinst:ospfv2/oc-netinst:areas/oc-netinst:area/oc-netinst:lsdb" +
            "/oc-netinst:lsa-types/oc-netinst:lsa-type/oc-netinst:lsas/oc-ospfv2-ext:lsa-ext" +
            "/oc-ospfv2-ext:opaque-lsa/oc-ospfv2-ext:traffic-engineering" {
            deviate not-supported;
  }
  deviation "/oc-netinst:network-instances/oc-netinst:network-instance/oc-netinst:protocols" +
            "/oc-netinst:protocol/oc-netinst:ospfv2/oc-netinst:areas/oc-netinst:area/oc-netinst:lsdb" +
            "/oc-netinst:lsa-types/oc-netinst:lsa-type/oc-netinst:lsas/oc-ospfv2-ext:lsa-ext" +
            "/oc-ospfv2-ext:opaque-lsa/oc-ospfv2-ext:grace-lsa" {
            deviate not-supported;
  }
  deviation "/oc-netinst:network-instances/oc-netinst:network-instance/oc-netinst:protocols" +
            "/oc-netinst:protocol/oc-netinst:ospfv2/oc-netinst:areas/oc-netinst:area/oc-netinst:lsdb" +
            "/oc-netinst:lsa-types/oc-netinst:lsa-type/oc-netinst:lsas/oc-ospfv2-ext:lsa-ext" +
            "/oc-ospfv2-ext:opaque-lsa/oc-ospfv2-ext:router-information" {
            deviate not-supported;
  }
  deviation "/oc-netinst:network-instances/oc-netinst:network-instance/oc-netinst:protocols" +
            "/oc-netinst:protocol/oc-netinst:ospfv2/oc-netinst:areas/oc-netinst:area/oc-netinst:lsdb" + 
            "/oc-netinst:lsa-types/oc-netinst:lsa-type/oc-netinst:lsas/oc-ospfv2-ext:lsa-ext" + 
            "/oc-ospfv2-ext:opaque-lsa/oc-ospfv2-ext:extended-prefix" {
            deviate not-supported;
  }
  deviation "/oc-netinst:network-instances/oc-netinst:network-instance/oc-netinst:protocols" +
            "/oc-netinst:protocol/oc-netinst:ospfv2/oc-netinst:areas/oc-netinst:area/oc-netinst:lsdb" + 
            "/oc-netinst:lsa-types/oc-netinst:lsa-type/oc-netinst:lsas/oc-ospfv2-ext:lsa-ext" +
            "/oc-ospfv2-ext:opaque-lsa/oc-ospfv2-ext:extended-link" {
            deviate not-supported;
  }
  deviation "/oc-netinst:network-instances/oc-netinst:network-instance/oc-netinst:protocols" +
            "/oc-netinst:protocol/oc-netinst:ospfv2/oc-netinst:areas/oc-netinst:area/oc-netinst:lsdb" +
            "/oc-netinst:lsa-types/oc-netinst:lsa-type/oc-netinst:lsas/oc-ospfv2-ext:lsa-ext" + 
            "/oc-ospfv2-ext:opaque-lsa/oc-ospfv2-ext:unknown-tlv" {
            deviate not-supported;
  }
  deviation "/oc-netinst:network-instances/oc-netinst:network-instance/oc-netinst:protocols" +
            "/oc-netinst:protocol/oc-netinst:ospfv2/oc-netinst:areas/oc-netinst:area/oc-netinst:lsdb" +
            "/oc-netinst:lsa-types/oc-netinst:lsa-type/oc-netinst:lsas/oc-ospfv2-ext:lsa-ext/oc-ospfv2-ext:nssa-external-lsa" {
            deviate not-supported;
  } 
  /* SONIC-83272: Mark as not-supported attributes related to OSPF opaque-lsa and NSSA-lsa in yang lsdb: End */

  augment "/oc-netinst:network-instances/oc-netinst:network-instance" +
          "/oc-netinst:protocols/oc-netinst:protocol/oc-netinst:ospfv2" {
    description
      "extra parameters related to ospfv2 route table state information";
    uses ospfv2-ext-route-tables-state;
  }

  /* OSPFv2 global deviations and augmentions */
  deviation "/oc-netinst:network-instances/oc-netinst:network-instance" +
          "/oc-netinst:protocols/oc-netinst:protocol/oc-netinst:ospfv2" +
          "/oc-netinst:global/oc-netinst:config" +
          "/oc-ospfv2-ext:description" {
        deviate not-supported;
  }
  deviation "/oc-netinst:network-instances/oc-netinst:network-instance" +
          "/oc-netinst:protocols/oc-netinst:protocol/oc-netinst:ospfv2" +
          "/oc-netinst:global/oc-netinst:state" +
          "/oc-ospfv2-ext:description" {
        deviate not-supported;
  }

  /* OSPFv2 Area interace deviationa and augmentions */

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:id"  {
    deviate replace {
      type leafref {
        path "/oc-if:interfaces/oc-if:interface/oc-if:name";
      }
    }
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:config" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:interface-ref" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:timers/oc-netinst:config" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:mpls" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:lsa-filter" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:state/oc-netinst:hide-network" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:state" +
          "/oc-netinst:multi-area-adjacency-primary" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:state" +
          "/oc-netinst:metric" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:neighbors" {
    deviate not-supported;
  }

  augment "/oc-netinst:network-instances/oc-netinst:network-instance" +
          "/oc-netinst:protocols/oc-netinst:protocol/oc-netinst:ospfv2" +
          "/oc-netinst:areas/oc-netinst:area/oc-netinst:interfaces" +
          "/oc-netinst:interface/oc-netinst:state" {
    description
      "extra parameters related to ospfv2 areas area interfaces interface state";
    uses ospfv2-ext-area-interface-config;
    uses oc-ospf-ext:ospf-ext-area-interface-state;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:enable-bfd/oc-netinst:config" {
    deviate not-supported;
  }

  deviation "/oc-netinst:network-instances/oc-netinst:network-instance" +
          "/oc-netinst:protocols/oc-netinst:protocol/oc-netinst:ospfv2" +
          "/oc-netinst:areas/oc-netinst:area/oc-netinst:interfaces" +
          "/oc-netinst:interface/oc-netinst:enable-bfd/oc-netinst:state" +
          "/oc-netinst:check-control-plane-failure" {
    deviate not-supported;
  }

  augment "/oc-netinst:network-instances/oc-netinst:network-instance" +
          "/oc-netinst:protocols/oc-netinst:protocol/oc-netinst:ospfv2" +
          "/oc-netinst:areas/oc-netinst:area/oc-netinst:interfaces" +
          "/oc-netinst:interface/oc-netinst:timers/oc-netinst:state" {
    description
      "extra parameters related to ospfv2 areas area interfaces interface timers state";
    uses oc-ospf-ext:ospf-ext-area-interface-timers-config;
    uses oc-ospf-ext:ospf-ext-area-interface-timers-state;
  }

  augment "/oc-netinst:network-instances/oc-netinst:network-instance" +
          "/oc-netinst:protocols/oc-netinst:protocol/oc-netinst:ospfv2" +
          "/oc-netinst:areas/oc-netinst:area/oc-netinst:interfaces" +
          "/oc-netinst:interface" {
    description
      "extra parameters related to ospfv2 areas area interfaces interface";
    uses oc-ospf-ext:ospf-ext-area-interface-neighbors-state;
    uses oc-ospf-ext:ospf-ext-area-interface-message-stats-top;
  }

  /* OSPF area lsdb lsa deviation and augmentaion */
  deviation "/oc-netinst:network-instances/oc-netinst:network-instance" +
            "/oc-netinst:protocols/oc-netinst:protocol/oc-netinst:ospfv2" +
            "/oc-netinst:areas/oc-netinst:area/oc-netinst:lsdb" +
            "/oc-netinst:lsa-types/oc-netinst:lsa-type/oc-netinst:lsas" +
            "/oc-netinst:lsa" {
    deviate not-supported;
  }

  augment "/oc-netinst:network-instances/oc-netinst:network-instance" +
          "/oc-netinst:protocols/oc-netinst:protocol/oc-netinst:ospfv2" +
          "/oc-netinst:areas/oc-netinst:area/oc-netinst:lsdb" +
          "/oc-netinst:lsa-types/oc-netinst:lsa-type/oc-netinst:lsas" {
    description
      "extra parameters related to ospfv2 lsa under areas area lsdb";
    uses ospfv2-ext-area-lsdb-lsa-state;
  }

  /* OSPF interface augmentaion under interface ipv4 */

  augment "/oc-if:interfaces/oc-if:interface/oc-if:subinterfaces/oc-if:subinterface/oc-ip:ipv4" {
    description
      "extra parameters related to interfaces interface subinterfaces subinterface ipv4";
    uses ospfv2-ext-interface-phys-config;
  }

  deviation "/oc-if:interfaces/oc-if:interface/oc-if:subinterfaces/oc-if:subinterface" +
            "/oc-ip:ipv4/oc-ospfv2-ext:ospfv2/oc-ospfv2-ext:if-addresses" +
            "/oc-ospfv2-ext:config/oc-ospfv2-ext:metric" {
    deviate replace {
      type oc-ospf-ext:ospf-cost-metric;
    }
  }

  deviation "/oc-netinst:network-instances/oc-netinst:network-instance" +
            "/oc-netinst:protocols/oc-netinst:protocol/oc-netinst:ospfv2" +
            "/oc-netinst:areas/oc-netinst:area/oc-netinst:lsdb" +
            "/oc-netinst:lsa-types/oc-netinst:lsa-type/oc-netinst:lsas" +
            "/oc-ospfv2-ext:lsa-ext/oc-ospfv2-ext:state/oc-ospfv2-ext:sequence-number"  {
    deviate not-supported;
  }

  deviation "/oc-if:interfaces/oc-if:interface/oc-if:subinterfaces/oc-if:subinterface" +
            "/oc-ip:ipv4/oc-ospfv2-ext:ospfv2/oc-ospfv2-ext:if-addresses" +
            "/oc-ospfv2-ext:config/oc-ospfv2-ext:passive" {
    deviate not-supported;
  }

  deviation "/oc-if:interfaces/oc-if:interface/oc-if:subinterfaces/oc-if:subinterface" +
            "/oc-ip:ipv4/oc-ospfv2-ext:ospfv2/oc-ospfv2-ext:if-addresses" +
            "/oc-ospfv2-ext:config/oc-ospfv2-ext:hide-network" {
    deviate not-supported;
  }
  
  deviation "/oc-if:interfaces/oc-if:interface/oc-if:subinterfaces/oc-if:subinterface" +
            "/oc-ip:ipv4/oc-ospfv2-ext:ospfv2/oc-ospfv2-ext:if-addresses" +
            "/oc-ospfv2-ext:config/oc-ospfv2-ext:id" {
    deviate not-supported;
  }
  
  deviation "/oc-if:interfaces/oc-if:interface/oc-if:subinterfaces/oc-if:subinterface" +
            "/oc-ip:ipv4/oc-ospfv2-ext:ospfv2/oc-ospfv2-ext:if-addresses" +
            "/oc-ospfv2-ext:config/oc-ospfv2-ext:multi-area-adjacency-primary" {
    deviate not-supported;
  }
  
  deviation "/oc-if:interfaces/oc-if:interface/oc-if:subinterfaces/oc-if:subinterface" +
            "/oc-ip:ipv4/oc-ospfv2-ext:ospfv2/oc-ospfv2-ext:if-addresses" +
            "/oc-ospfv2-ext:state/oc-ospfv2-ext:passive" {
    deviate not-supported;
  }

  deviation "/oc-if:interfaces/oc-if:interface/oc-if:subinterfaces/oc-if:subinterface" +
            "/oc-ip:ipv4/oc-ospfv2-ext:ospfv2/oc-ospfv2-ext:if-addresses" +
            "/oc-ospfv2-ext:state/oc-ospfv2-ext:hide-network" {
    deviate not-supported;
  }
  
  deviation "/oc-if:interfaces/oc-if:interface/oc-if:subinterfaces/oc-if:subinterface" +
            "/oc-ip:ipv4/oc-ospfv2-ext:ospfv2/oc-ospfv2-ext:if-addresses" +
            "/oc-ospfv2-ext:state/oc-ospfv2-ext:id" {
    deviate not-supported;
  }
  
  deviation "/oc-if:interfaces/oc-if:interface/oc-if:subinterfaces/oc-if:subinterface" +
            "/oc-ip:ipv4/oc-ospfv2-ext:ospfv2/oc-ospfv2-ext:if-addresses" +
            "/oc-ospfv2-ext:state/oc-ospfv2-ext:multi-area-adjacency-primary" {
    deviate not-supported;
  }

  deviation "/oc-if:interfaces/oc-if:interface/oc-if:subinterfaces/oc-if:subinterface" +
            "/oc-ip:ipv4/oc-ospfv2-ext:ospfv2/oc-ospfv2-ext:if-addresses" +
            "/oc-ospfv2-ext:enable-bfd/oc-ospfv2-ext:config" +
            "/oc-ospfv2-ext:check-control-plane-failure" {
    deviate not-supported;
  }

  deviation "/oc-if:interfaces/oc-if:interface/oc-if:subinterfaces/oc-if:subinterface" +
            "/oc-ip:ipv4/oc-ospfv2-ext:ospfv2/oc-ospfv2-ext:if-addresses" +
            "/oc-ospfv2-ext:enable-bfd/oc-ospfv2-ext:state" +
            "/oc-ospfv2-ext:check-control-plane-failure" {
    deviate not-supported;
  }

  deviation "/oc-if:interfaces/oc-if:interface/oc-if:subinterfaces/oc-if:subinterface" +
            "/oc-ip:ipv4/oc-ip:unnumbered/oc-ip:config" +
            "/oc-ip:enabled" {
    deviate not-supported;
  }

   deviation "/oc-if:interfaces/oc-if:interface/oc-if:subinterfaces/oc-if:subinterface" +
            "/oc-ip:ipv4/oc-ip:unnumbered/oc-ip:state" +
            "/oc-ip:enabled" {
    deviate not-supported;
  }

  augment "/oc-if:interfaces/oc-if:interface/oc-vlan:routed-vlan/oc-ip:ipv4" {
    description
      "extra parameters related to interfaces interface subinterfaces subinterface ipv4";
    uses ospfv2-ext-interface-phys-config;
  }

  deviation "/oc-if:interfaces/oc-if:interface/oc-vlan:routed-vlan" +
            "/oc-ip:ipv4/oc-ospfv2-ext:ospfv2/oc-ospfv2-ext:if-addresses" +
            "/oc-ospfv2-ext:config/oc-ospfv2-ext:metric" {
    deviate replace {
      type oc-ospf-ext:ospf-cost-metric;
    }
  }

  deviation "/oc-if:interfaces/oc-if:interface/oc-vlan:routed-vlan/oc-ip:ipv4" +
            "/oc-ospfv2-ext:ospfv2/oc-ospfv2-ext:if-addresses" +
            "/oc-ospfv2-ext:enable-bfd/oc-ospfv2-ext:config" +
            "/oc-ospfv2-ext:check-control-plane-failure" {
    deviate not-supported;
  }

  deviation "/oc-if:interfaces/oc-if:interface/oc-vlan:routed-vlan/oc-ip:ipv4" +
            "/oc-ospfv2-ext:ospfv2/oc-ospfv2-ext:if-addresses" +
            "/oc-ospfv2-ext:enable-bfd/oc-ospfv2-ext:state" +
            "/oc-ospfv2-ext:check-control-plane-failure" {
    deviate not-supported;
  }

  deviation "/oc-if:interfaces/oc-if:interface/oc-vlan:routed-vlan" +
            "/oc-ip:ipv4/oc-ospfv2-ext:ospfv2/oc-ospfv2-ext:if-addresses" +
            "/oc-ospfv2-ext:config/oc-ospfv2-ext:passive" {
    deviate not-supported;
  }

  deviation "/oc-if:interfaces/oc-if:interface/oc-vlan:routed-vlan" +
            "/oc-ip:ipv4/oc-ospfv2-ext:ospfv2/oc-ospfv2-ext:if-addresses" +
            "/oc-ospfv2-ext:config/oc-ospfv2-ext:hide-network" {
    deviate not-supported;
  }
  
  deviation "/oc-if:interfaces/oc-if:interface/oc-vlan:routed-vlan" +
            "/oc-ip:ipv4/oc-ospfv2-ext:ospfv2/oc-ospfv2-ext:if-addresses" +
            "/oc-ospfv2-ext:config/oc-ospfv2-ext:id" {
    deviate not-supported;
  }
  
  deviation "/oc-if:interfaces/oc-if:interface/oc-vlan:routed-vlan" +
            "/oc-ip:ipv4/oc-ospfv2-ext:ospfv2/oc-ospfv2-ext:if-addresses" +
            "/oc-ospfv2-ext:config/oc-ospfv2-ext:multi-area-adjacency-primary" {
    deviate not-supported;
  }
  
  deviation "/oc-if:interfaces/oc-if:interface/oc-vlan:routed-vlan" +
            "/oc-ip:ipv4/oc-ospfv2-ext:ospfv2/oc-ospfv2-ext:if-addresses" +
            "/oc-ospfv2-ext:state/oc-ospfv2-ext:passive" {
    deviate not-supported;
  }

  deviation "/oc-if:interfaces/oc-if:interface/oc-vlan:routed-vlan" +
            "/oc-ip:ipv4/oc-ospfv2-ext:ospfv2/oc-ospfv2-ext:if-addresses" +
            "/oc-ospfv2-ext:state/oc-ospfv2-ext:hide-network" {
    deviate not-supported;
  }
  
  deviation "/oc-if:interfaces/oc-if:interface/oc-vlan:routed-vlan" +
            "/oc-ip:ipv4/oc-ospfv2-ext:ospfv2/oc-ospfv2-ext:if-addresses" +
            "/oc-ospfv2-ext:state/oc-ospfv2-ext:id" {
    deviate not-supported;
  }
  
  deviation "/oc-if:interfaces/oc-if:interface/oc-vlan:routed-vlan" +
            "/oc-ip:ipv4/oc-ospfv2-ext:ospfv2/oc-ospfv2-ext:if-addresses" +
            "/oc-ospfv2-ext:state/oc-ospfv2-ext:multi-area-adjacency-primary" {
    deviate not-supported;
  }

  deviation "/oc-if:interfaces/oc-if:interface/oc-vlan:routed-vlan" +
            "/oc-ip:ipv4/oc-ip:unnumbered/oc-ip:config" +
            "/oc-ip:enabled" {
    deviate not-supported;
  }

  deviation "/oc-if:interfaces/oc-if:interface/oc-vlan:routed-vlan" +
            "/oc-ip:ipv4/oc-ip:unnumbered/oc-ip:state" +
            "/oc-ip:enabled" {
    deviate not-supported;
  }
}
