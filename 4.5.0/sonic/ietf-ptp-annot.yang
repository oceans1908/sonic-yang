module ietf-ptp-annot {

    yang-version "1.1";

    namespace "http://openconfig.net/yang/annotation/ptp-annot";
    prefix "ptp-annot";

    import sonic-extensions { prefix sonic-ext; }
    import ietf-interfaces { prefix if; }
    import ietf-ptp { prefix ptp; }
    import ietf-ptp-ext { prefix ptp-ext; }

	deviation /ptp:ptp {
		deviate add {
			sonic-ext:user-role-priv "write:netadmin";
			sonic-ext:pre-transformer "ptp_pre_xfmr";
			sonic-ext:post-transformer "ptp_post_xfmr";
		}
	}

	deviation /ptp:ptp/ptp:instance-list {
		deviate add {
			sonic-ext:table-name "PTP_INSTANCE";
			sonic-ext:key-transformer "ptp_global_key_xfmr";
		}
	}

	deviation /ptp:ptp/ptp:instance-list/ptp:current-ds {
		deviate add {
			sonic-ext:table-name "PTP_CURRENTDS";
			sonic-ext:key-transformer "ptp_global_key_xfmr";
			sonic-ext:db-name "STATE_DB";
		}
	}

	deviation /ptp:ptp/ptp:instance-list/ptp:parent-ds {
		deviate add {
			sonic-ext:table-name "PTP_PARENTDS";
			sonic-ext:key-transformer "ptp_global_key_xfmr";
			sonic-ext:db-name "STATE_DB";
		}
	}

	deviation /ptp:ptp/ptp:instance-list/ptp-ext:ptp-debug {
		deviate add {
			sonic-ext:subtree-transformer "ptp_debug_xfmr";
		}
	}

	deviation /ptp:ptp/ptp:instance-list/ptp:parent-ds/ptp:grandmaster-identity {
		deviate add {
			sonic-ext:field-transformer "ptp_clock_identity_xfmr";
		}
	}

	deviation /ptp:ptp/ptp:instance-list/ptp:parent-ds/ptp:parent-port-identity/ptp:clock-identity {
		deviate add {
			sonic-ext:field-transformer "ptp_clock_identity_xfmr";
		}
	}

	deviation /ptp:ptp/ptp:instance-list/ptp:parent-ds/ptp:grandmaster-clock-quality/ptp:offset-scaled-log-variance {
		deviate add {
		}
	}

	deviation /ptp:ptp/ptp:instance-list/ptp:parent-ds/ptp:parent-stats {
		deviate add {
			sonic-ext:field-transformer "ptp_boolean_xfmr";
		}
	}

	deviation /ptp:ptp/ptp:instance-list/ptp:time-properties-ds {
		deviate add {
			sonic-ext:table-name "PTP_TIMEPROPDS";
			sonic-ext:key-transformer "ptp_global_key_xfmr";
			sonic-ext:db-name "STATE_DB";
		}
	}

	deviation /ptp:ptp/ptp:instance-list/ptp-ext:servo-status-info {
		deviate add {
			sonic-ext:table-name "PTP_SERVO_STATUS";
			sonic-ext:subtree-transformer "ptp_servo_status_xfmr";
			sonic-ext:db-name "STATE_DB";
		}
	}
	
	deviation /ptp:ptp/ptp:instance-list/ptp:time-properties-ds/ptp:time-traceable {
		deviate add {
			sonic-ext:field-transformer "ptp_boolean_xfmr";
		}
	}

	deviation /ptp:ptp/ptp:instance-list/ptp:time-properties-ds/ptp:frequency-traceable {
		deviate add {
			sonic-ext:field-transformer "ptp_boolean_xfmr";
		}
	}

	deviation /ptp:ptp/ptp:instance-list/ptp:time-properties-ds/ptp:ptp-timescale {
		deviate add {
			sonic-ext:field-transformer "ptp_boolean_xfmr";
		}
	}

	deviation /ptp:ptp/ptp:instance-list/ptp:time-properties-ds/ptp:current-utc-offset-valid {
		deviate add {
			sonic-ext:field-transformer "ptp_boolean_xfmr";
		}
	}

	deviation /ptp:ptp/ptp:instance-list/ptp:time-properties-ds/ptp:leap59 {
		deviate add {
			sonic-ext:field-transformer "ptp_boolean_xfmr";
		}
	}

	deviation /ptp:ptp/ptp:instance-list/ptp:time-properties-ds/ptp:leap61 {
		deviate add {
			sonic-ext:field-transformer "ptp_boolean_xfmr";
		}
	}

	deviation /ptp:ptp/ptp:instance-list/ptp:port-ds-list {
		deviate add {
			sonic-ext:table-name "PTP_PORT";
			sonic-ext:subtree-transformer "ptp_port_ds_xfmr";
			sonic-ext:db-name "STATE_DB";
		}
	}

	deviation /ptp:ptp/ptp:instance-list/ptp:instance-number {
		deviate add {
			sonic-ext:field-transformer "ptp_inst_number_xfmr";
		}
	}

	deviation /ptp:ptp/ptp:instance-list/ptp:default-ds {
		deviate add {
			sonic-ext:table-name "PTP_CLOCK";
			sonic-ext:key-transformer "ptp_entry_key_xfmr";
		}
	}

	deviation /ptp:ptp/ptp:instance-list/ptp:default-ds/ptp-ext:clock-type {
		deviate add {
			sonic-ext:field-name "clock-type";
		}
	}

	deviation /ptp:ptp/ptp:instance-list/ptp:default-ds/ptp:slave-only {
		deviate add {
			sonic-ext:field-transformer "ptp_boolean_xfmr";
		}
	}

	deviation /ptp:ptp/ptp:instance-list/ptp:default-ds/ptp:two-step-flag {
		deviate add {
			sonic-ext:field-transformer "ptp_boolean_xfmr";
		}
	}

	deviation /ptp:ptp/ptp:instance-list/ptp:default-ds/ptp:clock-identity {
		deviate add {
			sonic-ext:field-transformer "ptp_clock_identity_xfmr";
		}
	}

    deviation /ptp:ptp/ptp:instance-list/ptp:default-ds/ptp:clock-quality/ptp:clock-class {
      deviate add {
			sonic-ext:field-transformer "ptp_clock_quality_xfmr";
      }
    }

    deviation /ptp:ptp/ptp:instance-list/ptp:default-ds/ptp:clock-quality/ptp:clock-accuracy {
      deviate add {
			sonic-ext:field-transformer "ptp_clock_quality_xfmr";
      }
    }

    deviation /ptp:ptp/ptp:instance-list/ptp:default-ds/ptp:clock-quality/ptp:offset-scaled-log-variance {
      deviate add {
			sonic-ext:field-transformer "ptp_clock_quality_xfmr";
      }
    }

	deviation /ptp:ptp/ptp:instance-list/ptp:default-ds/ptp-ext:network-transport {
		deviate add {
			sonic-ext:field-transformer "ptp_network_transport_xfmr";
		}
	}

	deviation /ptp:ptp/ptp:instance-list/ptp:default-ds/ptp:domain-number {
		deviate add {
			sonic-ext:field-transformer "ptp_domain_number_xfmr";
		}
	}

    deviation /ptp:ptp/ptp:instance-list/ptp:default-ds/ptp:number-ports {
      deviate add {
           sonic-ext:field-transformer "ptp_number_ports_xfmr";
      }
    }

	deviation /ptp:ptp/ptp:instance-list/ptp:default-ds/ptp-ext:clock-type {
		deviate add {
			sonic-ext:field-transformer "ptp_clock_type_xfmr";
		}
	}

	deviation /ptp:ptp/ptp:instance-list/ptp:default-ds/ptp-ext:domain-profile {
		deviate add {
			sonic-ext:field-transformer "ptp_domain_profile_xfmr";
		}
	}

	deviation /ptp:ptp/ptp:instance-list/ptp:default-ds/ptp-ext:unicast-multicast {
		deviate add {
			sonic-ext:field-transformer "ptp_unicast_multicast_xfmr";
		}
	}

	deviation /ptp:ptp/ptp:instance-list/ptp:default-ds/ptp-ext:udp6-scope {
		deviate add {
			sonic-ext:field-transformer "ptp_udp6_scope_xfmr";
		}
	}

	deviation /ptp:ptp/ptp:instance-list/ptp:default-ds/ptp-ext:source-interface {
		deviate add {
			sonic-ext:field-name "source-interface";
		}
	}

	/* currently unsupported
	deviation /ptp:ptp/ptp:transparent-clock-port-ds-list {
		deviate add {
			sonic-ext:table-name "PTP_TC_PORT";
			sonic-ext:key-transformer "ptp_tcport_entry_key_xfmr";
		}
	}

	deviation /ptp:ptp/ptp:transparent-clock-port-ds-list/ptp:faulty-flag {
		deviate add {
			sonic-ext:field-transformer "ptp_boolean_xfmr";
		}
	}

	deviation /ptp:ptp/ptp:transparent-clock-default-ds {
		deviate add {
			sonic-ext:table-name "PTP_TC_CLOCK";
			sonic-ext:key-transformer "ptp_global_key_xfmr";
		}
	}

	deviation /ptp:ptp/ptp:transparent-clock-default-ds/ptp:clock-identity {
		deviate add {
			sonic-ext:field-transformer "ptp_clock_identity_xfmr";
		}
	}

	deviation /ptp:ptp/ptp:transparent-clock-default-ds/ptp:delay-mechanism {
		deviate add {
			sonic-ext:field-transformer "ptp_delay_mech_xfmr";
		}
	}
	*/

}
