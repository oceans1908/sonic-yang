module openconfig-platform-software-ext {
  yang-version 1;

  // namespace

  namespace "http://openconfig.net/yang/platform-software/extension";
  prefix oc-pf-sw-ext;

  import openconfig-extensions {
    prefix oc-ext;
  }

  import openconfig-platform { prefix oc-pf; }

  organization
    "SONiC";

  contact
    "SONiC";

  description
    "SONIC Platform Software module extensions.";

  oc-ext:openconfig-version "1.0.0";

  revision 2021-11-09 {
    description
      "Initial revision.";
    reference
      "1.0.0";
  }

  grouping platform-software-state {
        description "Platform software fields";
        leaf software-version {
            type string;
            description "Software Version";
        }
        leaf product-version {
            type string;
            description "Product Version";
        }
        leaf distribution-version {
            type string;
            description "Debian Version";
        }
        leaf kernel-version {
            type string;
            description "Kernel Version";
        }
        leaf config-db-version {
            type string;
            description "Configuration Database Version";
        }
        leaf product-description {
            type string;
            description "Product Description";
        }
        leaf build-commit {
            type string;
            description "Build Commit ID";
        }
        leaf build-date {
            type string;
            description "Date of Build commit";
        }
        leaf built-by {
            type string;
            description "Built by";
        }
        leaf platform-name {
            type string;
            description "Platform Name";
        }
        leaf hwsku-version {
            type string;
            description "Hardware SKU version";
        }
        leaf asic-version {
            type string;
            description "asic version";
        }
        leaf hardware-version {
            type string;
            description "Hardware Version";
        }
        leaf serial-number {
            type string;
            description "Serial Number of Software";
        }
        leaf up-time {
            type string;
            description "System up-time";
        }
        leaf mfg-name {
            type string;
            description "Manufacturing Name";
        }
    }

  augment /oc-pf:components/oc-pf:component/oc-pf:software-module/oc-pf:state {
    description
        "Add attributes for software state information";

    uses platform-software-state;
  }

  augment /oc-pf:components/oc-pf:component/oc-pf:software-module {
    description
        "Add docker container";

    container docker {
      config false;
      description "docker information";

      list docker-version {
        key "docker-name";
        description "list of docker and their versions";
        leaf docker-name {
          type leafref {
              path "../state/docker-name";
          }
          description
              "name of the docker";
        }
        container state {
          description "docker version state";
          leaf docker-name {
            type string;
            description
              "name of the docker";
          }

          leaf docker-tag-id{
            type string;
            description
              "version of the docker-image";
          }
          leaf docker-image-id {
            type string;
            description
              "Image ID of the docker";
          }
          leaf docker-size{
            type string;
            description
              "Size of the docker-image";
          }
        }
      }
    }
  }

  augment /oc-pf:components/oc-pf:component/oc-pf:software-module {
    description
        "Add secure-boot container";

    container secure-boot {
      description
        "Top-level container for secure boot state data";

      container state {
        config false;
        description
          "Operational state data for secure boot";

        leaf supported {
          type boolean;
          description "Indicates if the secure boot functionality is supported";
        }

        leaf status {
          type enumeration {
            enum ENABLED {
                description "SecureBoot functionality is enabled and active";
            }
            enum DISABLED {
              description "SecureBoot functionality is disabled";
            }
            enum NOT_SUPPORTED {
              description "SecureBoot functionality is not supported";
            }
          }
          description "Indicates if the secure boot feature status";
        }
      }
    }
  }

}
