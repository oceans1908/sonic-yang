module sonic-vlan-translation {

    yang-version 1.1;

    namespace "http://github.com/Azure/sonic-vlan-translation";
    prefix vlan-translation;

    import sonic-common {
        prefix scommon;
    }

    import sonic-port {
        prefix port;
    }

    import sonic-portchannel {
        prefix lag;
    }

    import sonic-vlan {
        prefix vlan;
    }

    import sonic-extension {
        prefix sonic-ext;
    }

    organization
        "SONiC";

    contact
        "SONiC";

    description "VLAN Translation YANG Module for SONiC OS";

    revision 2023-07-31 {
        description "Add CVLAN ids as key and remove stage";
    }

    revision 2021-12-15 {
        description "First Revision";
    }

    container sonic-vlan-translation {
        description "Top Level container for VLAN_TRANSLATION";
        container VLAN_TRANSLATION {
            description "VLAN_TRANSLATION part of config_db";

            list VLAN_TRANSLATION_LIST {

                key "ifname s_vlan cvlan_ids";
                sonic-ext:custom-validation IsVlanMappingConfigurable;
                sonic-ext:custom-validation IsMultiFlowConfigurable;
                sonic-ext:custom-validation ValidateL2PTCoppExclVlanMappExists;
                description "List of translation parameters";

                leaf ifname {
                    type union {
                        type leafref {
                            path "/port:sonic-port/port:PORT/port:PORT_LIST/port:ifname";
                        }
                        type leafref {
                            path "/lag:sonic-portchannel/lag:PORTCHANNEL/lag:PORTCHANNEL_LIST/lag:name";
                        }
                    }
                    description "Interface name";
                }

                leaf s_vlan {
                    sonic-ext:custom-validation ValidateVlanConfig;
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                    description "Service VLAN";
                }

                leaf cvlan_ids {
                    type string {
                        pattern "(409[0-5]|40[0-8][0-9]|[1-3][0-9]{3}|[1-9][0-9]{2}|[1-9][0-9]|[1-9])|((409[0-5]|40[0-8][0-9]|[1-3][0-9]{3}|[1-9][0-9]{2}|[1-9][0-9]|[1-9])_(409[0-5]|40[0-8][0-9]|[1-3][0-9]{3}|[1-9][0-9]{2}|[1-9][0-9]|[1-9]))" {
                            error-message "Invalid Vlan name pattern";
                            error-app-tag vlan-name-invalid;
                        }
                    }
                    description 
                    "Represents single or double customer VLAN tags. Example  30 for single tag, 
                    and 60_70 for double tags, where 60 is outer CVLAN and 70 is inner CVLAN.";
                }

                leaf s_vlan_priority {
                    type uint8 {
                         range 0..7 {
                            error-message "Invalid VLAN Priority";
                            error-app-tag vlan-priority-invalid;
                         }
                    }
                    description "VLAN priority";
                }
                leaf multi_tag {
                    sonic-ext:custom-validation IsMultitagConfigurable;
                    type boolean;
                    description "Supports multitag(max 3 tag) traffic if true when SVLAN is mapped to VXLAN";
               }

            }
        }
    }
}
