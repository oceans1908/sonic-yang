module sonic-bgp-neighbor {
    namespace "http://github.com/Azure/sonic-bgp-neighbor";
    prefix sbnbr;
    yang-version 1.1;

    import ietf-inet-types {
        prefix inet;
    }

    import sonic-bgp-common {
        prefix sbc;
    }

    import sonic-port {
        prefix prt;
    }

    import sonic-portchannel {
        prefix spc;
    }

    import sonic-vlan {
        prefix svlan;
    }

    import sonic-bgp-global {
        prefix sbgpg;
    }

    import sonic-bgp-peergroup {
        prefix pg;
    }

    import sonic-interface {
        prefix sintf;
    }

    import sonic-extension {
        prefix sonic-ext;
    }

    organization
        "SONiC";

    contact
        "SONiC";

    description
        "SONIC BGP Neighbor";

    revision 2021-12-14 {
        description
            "v6only support for BGP neighbor.";
    }

    revision 2021-01-08 {
        description
            "Added support for routed vlan-sub-interface.";
    }

    revision 2019-09-23 {
        description
            "Initial revision.";
    }

    container sonic-bgp-neighbor {
        container BGP_NEIGHBOR {
            list BGP_NEIGHBOR_LIST {
                key "vrf_name neighbor";

                leaf vrf_name {
                    type leafref {
                        path "/sbgpg:sonic-bgp-global/sbgpg:BGP_GLOBALS/sbgpg:BGP_GLOBALS_LIST/sbgpg:vrf_name";
                    }
                    description "Network-instance/VRF name";
                }

                leaf neighbor {
                    type union {
                        type inet:ip-address;
                        type leafref {
                            path "/prt:sonic-port/prt:PORT/prt:PORT_LIST/prt:ifname";
                        }
                        type leafref {
                            path "/spc:sonic-portchannel/spc:PORTCHANNEL/spc:PORTCHANNEL_LIST/spc:name";
                        }
                        type leafref {
                            path "/sintf:sonic-interface/sintf:VLAN_SUB_INTERFACE/sintf:VLAN_SUB_INTERFACE_LIST/sintf:id";
                        }
                        type leafref {
                            path "/svlan:sonic-vlan/svlan:VLAN/svlan:VLAN_LIST/svlan:name";
                        }
                    }
                    description "Neighbor description, it will be neighbor address or interface name";
                }

                leaf v6only {
                    type boolean;
                    sonic-ext:custom-validation ValidateV6onlyNeighbor; 
                    description "Enable BGP with v6 link-local only";
                }

                leaf peer_group_name {
                    type leafref {
                        path "/pg:sonic-bgp-peergroup/pg:BGP_PEER_GROUP/pg:BGP_PEER_GROUP_LIST[pg:vrf_name=current()/../vrf_name]/pg:peer_group_name";
                    }
                    sonic-ext:custom-validation ValidateNeighborPeerGroup;
                    description "Peer group name";
                }

                uses sbc:sonic-bgp-cmn;
            }
        }

        container BGP_NEIGHBOR_AF {
            list BGP_NEIGHBOR_AF_LIST {
                key "vrf_name neighbor afi_safi";

                leaf vrf_name {
                    type leafref {
                        path "/sbgpg:sonic-bgp-global/sbgpg:BGP_GLOBALS/sbgpg:BGP_GLOBALS_LIST/sbgpg:vrf_name";
                    }
                    description "Network-instance/VRF name";
                }

                leaf neighbor {
                    type leafref {
                        path "../../../BGP_NEIGHBOR/BGP_NEIGHBOR_LIST[vrf_name=current()/../vrf_name]/neighbor";
                    }
                }
                uses sbc:sonic-bgp-cmn-af;
            }
        }
    }
}
