module sonic-image-management-annot {

    yang-version "1.1";

    namespace "http://openconfig.net/yang/annotation/sonic-image-management-annot";
    prefix "imgmt-annot"; 

    import sonic-extensions { prefix sonic-ext; }
    import sonic-image-management { prefix imgmt; }

    deviation /imgmt:sonic-image-management/imgmt:IMAGE_GLOBAL/imgmt:IMAGE_GLOBAL_LIST {
      deviate add {
        sonic-ext:db-name "STATE_DB";
      }
    }
    deviation /imgmt:sonic-image-management/imgmt:IMAGE_TABLE/imgmt:IMAGE_TABLE_LIST {
      deviate add {
        sonic-ext:db-name "STATE_DB";
      }
    }    
}
