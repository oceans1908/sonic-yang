module sonic-interface {
    namespace "http://github.com/Azure/sonic-interface";
    prefix sint;
    yang-version 1.1;

    import ietf-inet-types {
        prefix inet;
    }

    import sonic-port {
        prefix prt;
    }

    import sonic-vrf {
        prefix vrf;
    }

    import sonic-loopback-interface {
        prefix lointf;
    }

    import sonic-loopback {
        prefix lo;
    }

    import sonic-portchannel {
        prefix spc;
    }

    import sonic-common {
        prefix cmn;
    }

    import sonic-extension {
        prefix sonic-ext;
    }

    import sonic-interface-common {
        prefix sonic-if-cmn;
    }

    organization
        "SONiC";

    contact
        "SONiC";

    description
        "SONIC INTERFACE";

    revision 2022-12-21 {
        description
            "Add custom validation for vrf_name.";
    }

    revision 2020-07-26 {
        description
            "Modification for sonic-loopback.yang.";
    }
    revision 2020-04-07 {
        description
            "Add VRF and IP address attribute";
    }
    revision 2020-02-28 {
        description
            "Add DHCP server attribute";
    }
    revision 2020-02-15 {
        description
            "Add ipv6_use_link_local_only attribute to interface object";
    }
    revision 2019-12-01 {
        description
            "Add leafref for vrf_name.";
    }
    revision 2019-11-20 {
        description
            "Adding RPC for clear counters.";
    }
    revision 2019-07-02 {
        description
            "Initial revision.";
    }

/*
 * RPCs
*/
        rpc clear_counters {
            description "RPC for clearing interface counters. Input can be :
                       1. Single interface name
                       2. All interfaces
                       3. All interfaces of a particular type";

            input {
                leaf interface-param {
                    type string;
                        description
                            "parameter for clearing counters - all or interface type(Ethernet/PortChannel) or interface name";
                    }
            }
            output {
                leaf status {
                    type int32;
                    description
                        "The status of the operation execution request.";
                }
                leaf status-detail {
                    type string;
                    description
                        "The detailed status of the operation execution request.";
                }
            }
        }

        rpc clear_ip {

            description
                "Clears IPv4/IPv6 address assigned to a specific interface";
            input {
                leaf ifName {
                    type string;
                    description
                        "Interface with which IP address needs to be disassociated";
                }
                leaf ipPrefix {
                    type inet:ip-prefix;
                    description
                        "IP (v4/v6) address needs to be removed";
                }
                leaf secondary {
                    type boolean;
                    description "Indicates whether IP adddress configured is secondary or not";
                }
            }
            output {
                leaf status {
                    type uint32;
                    description
                        "Status of operation execution request";
                }
                leaf status-detail {
                    type string;
                    description
                        "Detailed status of operation execution request";
                }
            }
        }


    container sonic-interface {

        container INTERFACE {

            list INTERFACE_LIST {
                key "portname";
                sonic-ext:custom-validation ValidateDpbStatusForIpConfig;
                sonic-ext:custom-validation ValidatePacIntfCheck;
                sonic-ext:custom-validation ValidateVlanMapIntf;
                sonic-ext:custom-validation ValidateL2ConfigExists;

                leaf portname{
                    type leafref {
                        path "/prt:sonic-port/prt:PORT/prt:PORT_LIST/prt:ifname";
                    }
                }

                leaf vrf_name {
                    type union {
                        type string {
                            pattern "mgmt";
                        }
                        type leafref {
                            path "/vrf:sonic-vrf/vrf:VRF/vrf:VRF_LIST/vrf:vrf_name";
                        }
                    }

                    sonic-ext:custom-validation ValidateIntfVrfBinding;
                }

                leaf nat_zone {
                    type uint8 {
                        range "0..3";
                    }
                    must "((/cmn:operation/cmn:operation != 'CREATE') and (/cmn:operation/cmn:operation != 'UPDATE')) or " +
                        "(count(/sonic-interface/INTERFACE/INTERFACE_IPADDR_LIST[portname=current()/../portname]) > 1)"
                        {
                            error-message "NAT Zone can be configured on routing interface only";
                            error-app-tag nat-invalid-routing-interface;
                        }
                }

                leaf-list dhcp_servers {
                    max-elements 16;
                    type inet:ip-address;
                }

                leaf-list dhcpv6_servers{
                    max-elements 16;
                    type inet:ipv6-address;
                }

                leaf dhcp_relay_link_select {
                    type cmn:mode-enable;
                    must "((/cmn:operation/cmn:operation != 'CREATE') and (/cmn:operation/cmn:operation != 'UPDATE')) or " +
                         "(current()/../dhcp_relay_src_intf)"
                         {
                               error-message "DHCP relay source interface not configured or invalid operation";
                               error-app-tag dhcp-server-adress-config;
                         }
                }

                leaf dhcp_relay_src_intf {
                    type string;
                    must "((/cmn:operation/cmn:operation != 'CREATE') and (/cmn:operation/cmn:operation != 'UPDATE')) or " +
                         "(current()/../dhcp_servers)"
                         {
                               error-message "DHCP relay address not configured or invalid operation";
                               error-app-tag dhcp-server-adress-config;
                         }
                }

                leaf dhcp_relay_max_hop_count {
                    type uint32;
                    must "((/cmn:operation/cmn:operation != 'CREATE') and (/cmn:operation/cmn:operation != 'UPDATE')) or " +
                            "(current()/../dhcp_servers)"
                       {
                               error-message "DHCP relay address not configured";
                               error-app-tag dhcp-server-adress-config;
                       }
                }

                leaf dhcp_server_vrf {
                    type union {
                        type string {
                            pattern "mgmt";
                        }
                        type leafref {
                            path "/vrf:sonic-vrf/vrf:VRF/vrf:VRF_LIST/vrf:vrf_name";
                        }
                    }
                    must "((/cmn:operation/cmn:operation != 'CREATE') and (/cmn:operation/cmn:operation != 'UPDATE')) or " +
                           "(current()/../dhcp_servers)"
                          {
                               error-message "DHCP server not configured";
                               error-app-tag dhcp-server-invalid-vrf-config;
                          }
                }

                leaf dhcp_relay_vrf_select {
                    type cmn:mode-enable;
                    must "((/cmn:operation/cmn:operation != 'CREATE') and (/cmn:operation/cmn:operation != 'UPDATE')) or " +
                            "(current()/../dhcp_servers)"
                       {
                               error-message "DHCP relay address not configured";
                               error-app-tag dhcp-server-adress-config;
                       }
                }

                leaf dhcp_relay_policy_action {
                    type cmn:relay-policy-action;
                    must "((/cmn:operation/cmn:operation != 'CREATE') and (/cmn:operation/cmn:operation != 'UPDATE')) or " +
                            "(current()/../dhcp_servers)"
                       {
                               error-message "DHCP relay address not configured";
                               error-app-tag dhcp-server-adress-config;
                       }
                }

                leaf dhcp_relay_smart_mode {
                    type cmn:mode-enable;
                    description "Enable/Disable smart relay mode on the interface.";
                    must "((/cmn:operation/cmn:operation != 'CREATE') and (/cmn:operation/cmn:operation != 'UPDATE')) or " +
                            "(current()/../dhcp_servers)"
                       {
                               error-message "DHCP relay address not configured";
                               error-app-tag dhcp-server-adress-config;
                       }
                }

                leaf dhcp_relay_circuit_id_format {
                    type string;
                    must "((/cmn:operation/cmn:operation != 'CREATE') and (/cmn:operation/cmn:operation != 'UPDATE')) or " +
                           "(current()/../dhcp_servers)"
                          {
                               error-message "DHCP server not configured";
                               error-app-tag dhcp-server-address-config;
                          }
                }

                leaf dhcpv6_relay_src_intf {
                    type string;
                    must "((/cmn:operation/cmn:operation != 'CREATE') and (/cmn:operation/cmn:operation != 'UPDATE')) or " +
                            "(current()/../dhcpv6_servers) "
                         {
                               error-message "DHCP relay address not configured";
                               error-app-tag dhcp-server-adress-config;
                         }

                }

                leaf dhcpv6_relay_max_hop_count {
                    type uint32;
                    must "((/cmn:operation/cmn:operation != 'CREATE') and (/cmn:operation/cmn:operation != 'UPDATE')) or " +
                            "(current()/../dhcpv6_servers) "
                         {
                               error-message "DHCP relay address not configured";
                               error-app-tag dhcp-server-adress-config;
                         }

                }

                leaf dhcpv6_server_vrf {
                    type union {
                        type string {
                            pattern "mgmt";
                        }
                        type leafref {
                            path "/vrf:sonic-vrf/vrf:VRF/vrf:VRF_LIST/vrf:vrf_name";
                        }
                    }
                    must "((/cmn:operation/cmn:operation != 'CREATE') and (/cmn:operation/cmn:operation != 'UPDATE')) or " +
                           "(current()/../dhcpv6_servers)"
                          {
                               error-message "DHCP server or src-intf not configured";
                               error-app-tag dhcp-server-invalid-vrf-config;
                          }
                }

                leaf dhcpv6_relay_vrf_select {
                    type cmn:mode-enable;
                    must "((/cmn:operation/cmn:operation != 'CREATE') and (/cmn:operation/cmn:operation != 'UPDATE')) or " +
                            "(current()/../dhcpv6_servers) "
                         {
                               error-message "DHCP relay address not configured";
                               error-app-tag dhcp-server-adress-config;
                         }
                }

                leaf ipv6_autoconfig {
                    type cmn:mode-enable;
                    default disable;
                    sonic-ext:custom-validation ValidateNdProxyexists;
					description
						"Enable IPv6 stateless auto-configuration on interface";
                }

                leaf ipv6_dad {
                    type cmn:dad-mode;
                    default disable;
                    description
                           "Enable/Disable IPv6 DAD on the interface";
                }

                leaf ipv6_use_link_local_only {
                    type cmn:mode-enable;
                    default disable;
                    description
                        "Enable IPv6 link local address on interface";
                    must "(current() = 'disable') or ((current() = 'enable') and count(/spc:sonic-portchannel/spc:PORTCHANNEL_MEMBER/spc:PORTCHANNEL_MEMBER_LIST[spc:ifname=current()/../portname]) = 0)"
                    {
                        error-message "Interface configured as a member of PortChannel. Cannot enable IPv6";
                        error-app-tag intf-po-member;
                    }
                }

                leaf unnumbered {
                    must "((/cmn:operation/cmn:operation != 'CREATE') and (/cmn:operation/cmn:operation != 'UPDATE')) or " +
                         "not(contains(/sonic-interface/INTERFACE/INTERFACE_IPADDR_LIST[portname=current()/../portname]/ip_prefix, '.'))"
                    {
                        error-message "Cannot configure IP address and IP Unnumbered interface configurations on the same interface";
                        error-app-tag intf-ip-config;
                    }

                    must "count(/spc:sonic-portchannel/spc:PORTCHANNEL_MEMBER/spc:PORTCHANNEL_MEMBER_LIST[spc:ifname=current()/../portname]) = 0"
                    {
                        error-message "Interface configured as a member of portchannel. Cannot configure IP Unnumbered";
                        error-app-tag intf-po-member;
                    }


                    sonic-ext:custom-validation ValidateIpv4UnnumIntf;
                    sonic-ext:custom-validation ValidateUnnumVrfMatch;
                    type leafref {
                        path "/lo:sonic-loopback/lo:LOOPBACK/lo:LOOPBACK_LIST/lo:name";
                    }
                }

                leaf-list helper_addresses {
                    type sonic-if-cmn:vrf-ip;
                    max-elements 4;
                    description
                        "List of destination addresses with each being a combination of Vrf and IP address";
                    must "((/cmn:operation/cmn:operation != 'CREATE') and (/cmn:operation/cmn:operation != 'UPDATE')) or " +
                         "(count(/sonic-interface/INTERFACE/INTERFACE_IPADDR_LIST[portname=current()/../portname]) > 1)"
                        {
                            error-message "Helper address can be configured on routing interface only";
                            error-app-tag helper-address-invalid-routing-interface;
                        }
                }
                leaf proxy_arp {
                     type cmn:proxy-mode;
                     sonic-ext:custom-validation ValidateIpv4ProxyArpIntf;
                     description
                         "Proxy-ARP config modes";
                }
                leaf nd_proxy {
                     type cmn:proxy-mode;
                     sonic-ext:custom-validation ValidateIpv6NdProxyIntf;
                     description
                        "ND-Proxy config modes";
                }
                leaf-list nd_proxy_rules {
                     type inet:ipv6-prefix;
                     sonic-ext:custom-validation ValidateIpv6NdProxyRules;
                     description
                        "Configuring the IPv6 prefixes for nd-proxy rules";
                }
            }

            list INTERFACE_IPADDR_LIST {
                key "portname ip_prefix";

                must "(/cmn:operation/cmn:operation != 'CREATE') or " +
                     "(not(contains(current()/ip_prefix, '.')) or "  +
                     "(count(current()/../INTERFACE_LIST[portname=current()/portname]/unnumbered) = 0))"
                {
                    error-message "Cannot configure IPv4 address and IP Unnumbered interface configurations on the same interface";
                    error-app-tag intf-unnum;
                }

                leaf portname{
                    type leafref {
                        path "../../INTERFACE_LIST/portname";
                    }
                }

                leaf eui64 {
                    type cmn:mode-enable;
                    default disable; 
                    description
                         "Controls the IPv6 Eui-64 identifier flag";
                }

                leaf ip_prefix {
                    type inet:ip-prefix;
                    sonic-ext:custom-validation ValidateIntfIp;
                    sonic-ext:custom-validation ValidateL2PTIntfIp;
                }
                leaf secondary {
                    type boolean;
                    description "Indicates whether IP adddress configured is secondary or not";
                }
            }
        }

        container INTF_TABLE {
            config false;
            list INTF_TABLE_LIST {
                key "ifName";

                leaf ifName {
                    type leafref {
                        path "/prt:sonic-port/prt:PORT/prt:PORT_LIST/prt:ifname";
                    }
                }

                leaf mtu {
                    type uint32;
                }

                leaf unnumbered {
                    type string;
                }

                leaf ipv6_dad {
                    default disable;
                    type cmn:dad-mode;
                }

                leaf ipv6_autoconfig {
                    default disable;
                    sonic-ext:custom-validation ValidateNdProxyexists;
                    type cmn:mode-enable;
                }

                leaf ipv6_use_link_local_only {
                    default disable;
                    type cmn:mode-enable;
                }

                leaf proxy_arp {
                     type cmn:proxy-mode;
                     sonic-ext:custom-validation ValidateIpv4ProxyArpIntf;
                     description
                         "Proxy-ARP config modes";
                }
                leaf nd_proxy {
                     type cmn:proxy-mode;
                     sonic-ext:custom-validation ValidateIpv6NdProxyIntf;
                     description
                        "ND-Proxy config modes";
                }
                leaf-list nd_proxy_rules {
                     type inet:ipv6-prefix;
                     sonic-ext:custom-validation ValidateIpv6NdProxyRules;
                     description
                        "Configuring the IPv6 prefixes for nd-proxy rules";
                }
            }

            list INTF_TABLE_IPADDR_LIST {
                key "ifName ipPrefix";

                leaf ifName {
                   type leafref {
                        path "/prt:sonic-port/prt:PORT/prt:PORT_LIST/prt:ifname";
                    }
                }

                leaf ipPrefix {
                    type inet:ip-prefix;
                }

                leaf secondary {
                    type boolean;
                }
             }
        }

        container VLAN_SUB_INTERFACE {
            list VLAN_SUB_INTERFACE_LIST {
                key "id";

                leaf id {
                    type string {
                        pattern '(Eth([1-3][0-9]{3}|[1-9][0-9]{2}|[1-9][0-9]|[0-9])' +
                                '|Eth([1-9]/(([1-9][0-9]{0,})|(([1-9][0-9]{0,})/([1-9][0-9]{0,}))))' +
                                '|Po([1-9]|[1-9][0-9]|1[0-9][0-9]|2[0-4][0-9]|25[0-6])' +
                                '|PortChannel([1-9]|[1-9][0-9]|1[0-9][0-9]|2[0-4][0-9]|25[0-6]))\.' +
                                '(6553[0-5]|655[0-2][0-9]|654[0-9]{2}|65[0-4][0-9]{2}|6[0-4][0-9]{3}|[1-5][0-9]{4}|[1-9][0-9]{1,3}|[0-9])' {
                            error-message "Invalid sub-interface name";
                            error-app-tag interface-name-invalid;
                        }
                    }
                    sonic-ext:custom-validation ValidateSubInterfaceIntf;
                }

                leaf parent {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                    mandatory true;
                }

                leaf vrf_name {
                    type union {
                        type string {
                            pattern "default";
                        }
                        type string {
                            pattern "mgmt";
                        }
                        type leafref {
                            path "/vrf:sonic-vrf/vrf:VRF/vrf:VRF_LIST/vrf:vrf_name";
                        }
                    }

                    sonic-ext:custom-validation ValidateIntfVrfBinding;
                }

                leaf vlan {
                    type uint16 {
                        range "1..4095" {
                            error-message "Vlan ID out of range";
                            error-app-tag vlanid-invalid;
                        }
                    }
                    sonic-ext:custom-validation ValidateSubInterfaceVlanID;
                }

                leaf admin_status {
                    type cmn:admin-status;
                }

                leaf description {
                    type string;
                }

                leaf ipv6_autoconfig {
                    type cmn:mode-enable;
                    sonic-ext:custom-validation ValidateNdProxyexists;
                    default disable;
                }

                leaf ipv6_dad {
                    type cmn:dad-mode;
                    default disable;
                    description
                        "Enable/Disable IPv6 DAD on the interface";
                }

                leaf ipv6_use_link_local_only {
                    type cmn:mode-enable;
                    default disable;
                    description
                        "Enable IPv6 link local address on interface";
                }

                leaf mtu{
                    type uint32 {
                        range "1312..9216" {
                            error-message "Invalid MTU value";
                            error-app-tag mtu-invalid;
                        }
                    }
                }

                leaf unnumbered {
                    must "((/cmn:operation/cmn:operation != 'CREATE') and (/cmn:operation/cmn:operation != 'UPDATE')) or " +
                         "not(contains(/sonic-interface/VLAN_SUB_INTERFACE/VLAN_SUB_INTERFACE_IPADDR_LIST[id=current()/../id]/ip_prefix, '.'))"
                    {
                        error-message "Cannot configure IP address and IP Unnumbered interface configurations on the same interface";
                        error-app-tag vlanintf-ip-config;
                    }

                    sonic-ext:custom-validation ValidateIpv4UnnumIntf;
                    sonic-ext:custom-validation ValidateUnnumVrfMatch;

                    type leafref {
                        path "/lo:sonic-loopback/lo:LOOPBACK/lo:LOOPBACK_LIST/lo:name";
                    }
                }

                leaf-list dhcp_servers {
                         max-elements 16;
                         type inet:ip-address;
                }

                leaf-list dhcpv6_servers {
                         max-elements 16;
                         type inet:ipv6-address;
                 }

                 leaf dhcp_relay_link_select {
                         type cmn:mode-enable;
                         must "((/cmn:operation/cmn:operation != 'CREATE') and (/cmn:operation/cmn:operation != 'UPDATE')) or " +
                              "(current()/../dhcp_relay_src_intf)"
                              {
                                    error-message "DHCP relay source interface not configured or invalid operation";
                                    error-app-tag dhcp-server-adress-config;
                              }
                 }

                 leaf dhcp_relay_src_intf {
                         type string;
                         must "((/cmn:operation/cmn:operation != 'CREATE') and (/cmn:operation/cmn:operation != 'UPDATE')) or " +
                                 "(current()/../dhcp_servers)"
                                 {
                                           error-message "DHCP relay address not configured or invalid operation";
                                           error-app-tag dhcp-server-adress-config;
                                 }
                  }

                  leaf dhcp_relay_max_hop_count {
                          type uint32;
                          must "((/cmn:operation/cmn:operation != 'CREATE') and (/cmn:operation/cmn:operation != 'UPDATE')) or " +
                                  "(current()/../dhcp_servers)"
                                  {
                                             error-message "DHCP relay address not configured";
                                             error-app-tag dhcp-server-adress-config;
                                  }
                   }

                   leaf dhcp_server_vrf {
                           type union {
                               type string {
                                   pattern "mgmt";
                               }
                               type leafref {
                                   path "/vrf:sonic-vrf/vrf:VRF/vrf:VRF_LIST/vrf:vrf_name";
                               }
                           }
                           must "((/cmn:operation/cmn:operation != 'CREATE') and (/cmn:operation/cmn:operation != 'UPDATE')) or " +
                                   "(current()/../dhcp_servers)"
                                   {
                                               error-message "DHCP server not configured";

                                               error-app-tag dhcp-server-invalid-vrf-config;
                                   }
                   }

                   leaf dhcp_relay_vrf_select {
                           type cmn:mode-enable;
                           must "((/cmn:operation/cmn:operation != 'CREATE') and (/cmn:operation/cmn:operation != 'UPDATE')) or " +
                                   "(current()/../dhcp_servers)"
                              {
                                      error-message "DHCP relay address not configured";
                                      error-app-tag dhcp-server-adress-config;
                              }
                   }

                   leaf dhcp_relay_policy_action {
                           type cmn:relay-policy-action;
                           must "((/cmn:operation/cmn:operation != 'CREATE') and (/cmn:operation/cmn:operation != 'UPDATE')) or " +
                                   "(current()/../dhcp_servers)"
                              {
                                      error-message "DHCP relay address not configured";
                                      error-app-tag dhcp-server-adress-config;
                              }
                   }

                   leaf dhcp_relay_smart_mode {
                           type cmn:mode-enable;
                           description "Enable/Disable smart relay mode on the interface.";
                           must "((/cmn:operation/cmn:operation != 'CREATE') and (/cmn:operation/cmn:operation != 'UPDATE')) or " +
                                   "(current()/../dhcp_servers)"
                              {
                                      error-message "DHCP relay address not configured";
                                      error-app-tag dhcp-server-adress-config;
                              }
                   }

                   leaf dhcp_relay_circuit_id_format {
                           type string;
                           must "((/cmn:operation/cmn:operation != 'CREATE') and (/cmn:operation/cmn:operation != 'UPDATE')) or " +
                                  "(current()/../dhcp_servers)"
                                  {
                                              error-message "DHCP server not configured";
                                              error-app-tag dhcp-server-address-config;
                                  }
                   }

                   leaf dhcpv6_relay_src_intf {
                           type string;
                           must "((/cmn:operation/cmn:operation != 'CREATE') and (/cmn:operation/cmn:operation != 'UPDATE')) or " +
                                   "(current()/../dhcpv6_servers) "
                                   {
                                               error-message "DHCP relay address not configured";
                                               error-app-tag dhcp-server-adress-config;
                                   }
                    }

                    leaf dhcpv6_relay_max_hop_count {
                            type uint32;
                            must "((/cmn:operation/cmn:operation != 'CREATE') and (/cmn:operation/cmn:operation != 'UPDATE')) or " +
                                    "(current()/../dhcpv6_servers) "
                                    {
                                                error-message "DHCP relay address not configured";
                                                error-app-tag dhcp-server-adress-config;
                                    }
                     }

                     leaf dhcpv6_server_vrf {
                            type union {
                                 type string {
                                     pattern "mgmt";
                                 }

                                 type leafref {
                                     path "/vrf:sonic-vrf/vrf:VRF/vrf:VRF_LIST/vrf:vrf_name";
                                 }
                            }
                             must "((/cmn:operation/cmn:operation != 'CREATE') and (/cmn:operation/cmn:operation != 'UPDATE')) or " +
                                      "(current()/../dhcpv6_servers)"
                                      {
                                                 error-message "DHCP server or src-intf not configured";
                                                 error-app-tag dhcp-server-invalid-vrf-config;
                                      }
                     }

                     leaf dhcpv6_relay_vrf_select {
                             type cmn:mode-enable;
                             must "((/cmn:operation/cmn:operation != 'CREATE') and (/cmn:operation/cmn:operation != 'UPDATE')) or " +
                                      "(current()/../dhcpv6_servers) "
                                      {
                                                error-message "DHCP relay address not configured";
                                                error-app-tag dhcp-server-adress-config;
                                      }
                     }

                     leaf proxy_arp {
                         type cmn:proxy-mode;
                         sonic-ext:custom-validation ValidateIpv4ProxyArpIntf;
                         description
                             "Proxy-ARP mode arguments";
                     }
                     leaf nd_proxy {
                         type cmn:proxy-mode;
                         sonic-ext:custom-validation ValidateIpv6NdProxyIntf;
                         description
                              "ND-Proxy mode arguments";
                     }
                     leaf-list nd_proxy_rules {
                         type inet:ipv6-prefix;
                         sonic-ext:custom-validation ValidateIpv6NdProxyRules;
                         description
                             "Configuring the IPv6 prefixes for nd-proxy rules";
                     }
            }

            list VLAN_SUB_INTERFACE_IPADDR_LIST {
                key "id ip_prefix";

                leaf id {
                    type leafref {
                        path "/sint:sonic-interface/sint:VLAN_SUB_INTERFACE/sint:VLAN_SUB_INTERFACE_LIST/sint:id";
                    }
                }

                leaf eui64 {
                    type cmn:mode-enable;
                    default disable;
                    description
                       "Controls the IPv6 Eui-64 identifier flag";
                }

                leaf ip_prefix {
                    type inet:ip-prefix;
                    sonic-ext:custom-validation ValidateIntfIp;
                }

                leaf secondary {
                    type boolean;
                    description "Indicates whether IP adddress configured is secondary or not";
                }

            }
        }
   }
}
