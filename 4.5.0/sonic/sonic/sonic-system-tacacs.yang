module sonic-system-tacacs {
    namespace "http://github.com/Azure/sonic-system-tacacs";
    prefix ssys;
    yang-version 1.1;

    import ietf-inet-types {
        prefix inet;
    }

    import sonic-port {
        prefix prt;
    }

    import sonic-portchannel {
        prefix spc;
    }

    import sonic-vlan {
        prefix svlan;
    }

    import sonic-loopback {
        prefix lo;
    }

    import sonic-interface {
        prefix sintf;
    }

    import sonic-mgmt-port {
        prefix smt;
    }

    import sonic-extension {
        prefix sonic-ext;
    }

    organization
        "SONiC";

    contact
        "SONiC";

    description
        "SONiC System TACACS";

    revision 2022-12-06 {
        description "Added cvl custom validation for TACAC+ server vrf configuration.";
    }

    revision 2021-01-08 {
        description "Added support for routed vlan-sub-interface.";
    }

    revision 2020-07-26 {
        description "Change for sonic-loopback.yang.";
    }

    revision 2020-05-02 {
        description "Allowed domain name as well for server configuration.";
    }

    revision 2020-02-17 {
        description "Allow special characters in passkey.";
    }

    revision 2019-11-13 {
        description "Initial revision.";
    }

    typedef auth_type_enumeration {
        type enumeration {
            enum pap;
            enum chap;
            enum mschap;
            enum login;
        }
    }

    container sonic-system-tacacs {

        container TACPLUS_SERVER {
            list TACPLUS_SERVER_LIST {
                max-elements 8;
                key "ipaddress";

                leaf ipaddress {
                    type inet:host;
                    sonic-ext:custom-validation ValidateIPAddressOrHostname;
                    description
                    "TACACS+ server's Domain name or IP address (IPv4 or IPv6)";
                }

                leaf priority {
                    default 1;
                    type uint8 {
                        range "1..64" {
                            error-message "TACACS server priority must be 1..64";
                        }
                    }
                }

                leaf tcp_port {
                    type inet:port-number;
                    default 49;
                }

                leaf timeout {
                    default 5;
                    type uint16 {
                        range "1..60" {
                            error-message "TACACS server timeout must be 1..60";
                        }
                    }
                }

                leaf auth_type {
                    type auth_type_enumeration;
                    default pap;
                }

                leaf passkey {
                    sonic-ext:custom-validation ValidateEncryptedKey;
                    type string;
                }

                leaf vrf {
                    type string {
                        pattern "mgmt|default" {
                            error-message "Error: Invalid VRF name";
                        }
                    }

                    sonic-ext:custom-validation ValidateMgmtVrfConfigured;
                    description
                        "Internal management vrf name for SONiC";
                }
            }
        }


        container TACPLUS {
            list TACPLUS_LIST {

                key "type";

                leaf type {
                    type enumeration {
                        enum global;
                    }
                }

                leaf auth_type {
                    type auth_type_enumeration;
                    default pap;
                }

                leaf timeout {
                    type uint16 {
                        range "1..60" {
                            error-message "TACACS timeout must be 1..60";
                        }
                    }
                    default 5;
                }

                leaf passkey {
                    sonic-ext:custom-validation ValidateEncryptedKey;
                    type string;
                }

                leaf src_intf {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/lo:sonic-loopback/lo:LOOPBACK/lo:LOOPBACK_LIST/lo:name";
                        }
                        type leafref {
                            path "/smt:sonic-mgmt-port/smt:MGMT_PORT/smt:MGMT_PORT_LIST/smt:ifname";
                        }
                        type leafref {
                            path "/sintf:sonic-interface/sintf:VLAN_SUB_INTERFACE/sintf:VLAN_SUB_INTERFACE_LIST/sintf:id";
                        }
                    }
                }
            }
        }
    }
}
