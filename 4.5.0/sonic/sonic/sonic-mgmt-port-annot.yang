module sonic-mgmt-port-annot {

    yang-version "1.1";

    namespace "http://openconfig.net/yang/annotation/mgmt-port-annot";
    prefix "mgmt-port-annot";

    import sonic-extensions { prefix sonic-ext; }
    import sonic-mgmt-port { prefix mgmt; }

    deviation /mgmt:sonic-mgmt-port/mgmt:MGMT_PORT_TABLE {
        deviate add {
            sonic-ext:db-name "APPL_DB";
        }
    }
    deviation /mgmt:sonic-mgmt-port/mgmt:MGMT_PORT/mgmt:MGMT_PORT_LIST/mgmt:ifname {
        deviate add {
            sonic-ext:value-transformer "alias_value_xfmr";
        }
    }
}
