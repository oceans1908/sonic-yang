module openconfig-pki-rpc {

  yang-version "1";

  // namespace
  namespace "http://openconfig.net/yang/pki-rpc/extension";

  prefix "oc-pki-rpc"; 

  import openconfig-extensions { prefix oc-ext; }
  
  // meta
  organization
    "OCP SONiC Subproject";

  contact
    "OCP SONiC Subproject Working Group
     https://github.com/Azure/SONiC";

  description
    "This module defines RPCs for pki";

  oc-ext:openconfig-version "0.2.0";

  revision "2024-08-29" {
    description
      "Add SSH keys generation and display RPCs";
    reference "0.2.0";
  }

  revision "2023-01-23" {
    description
      "Initial revision";
    reference "0.1.0";
  }
  oc-ext:regexp-posix;
    typedef rpcResult {
        description "Result code for pki operations";
        type enumeration {
            enum SUCCESS {
                description "The operation was successful.";
            }
            enum FAILED {
                description "The operation failed.";
            }
        }
    }
    typedef filename-uri-type {
       type string {
            pattern "((home|ftp|http|scp):.*)" {
                error-message "Invalid folder name.";
            }
            oc-ext:posix-pattern '((home|ftp|http|scp):.*)';
       }
        description
            "Pattern for safe access to the file system";
    }
  //rpcs
    rpc crypto-ca-cert-install {
        description "Install CA certificate";
        input {
            choice install-cert-file {
                description "File path or cert body contents.";
                mandatory true;
                
                leaf file-path {
                    description "Local or remote file uri.";
                    type filename-uri-type;
                }
                
                case cert-paste {
                    leaf file-contents {
                        description "Alternatively upload file as a string.";
                        type string;
                    }
                    leaf file-name {
                        description "File name if uploading as a string";
                        type string;
                    }
                }
            }
        }
        output {
            leaf status {
                type rpcResult;
                description
                    "The status of the operation execution request.";
            }
            leaf status-detail {
                type string;
                description
                    "The detailed status of the operation execution request.";
            }
            leaf subject-name {
                type string;
                description
                    "The subject name of the installed certificate.";
            }
            leaf issuer-name {
                type string;
                description
                    "The subject name of the installed certificate.";
            }
        }
    }
    rpc crypto-ca-cert-delete {
        description "Delete CA certificate";
        input {
            leaf file-name {
                description "CA Cert File name";
                type string;
            }
        }
        output {
            leaf status {
                type rpcResult;
                description
                    "The status of the operation execution request.";
            }

            leaf status-detail {
                type string;
                description
                    "The detailed status of the operation execution request.";
            }
        }
    }
rpc crypto-host-cert-install {
        description "Install Host certificate";
        input {
            leaf file-path {
                mandatory true;
                description "Local or remote certificate file uri.";
                type filename-uri-type;
            }
            leaf key-path {
                mandatory true;
                description "Local or remote key file uri.";
                type filename-uri-type;
            }
            leaf password {
                description "Password if key file is protected.";
                type string;
            }
            leaf fips-cert {
                type boolean;
                default false;
                description "Specifies if the certificate is FIPS compliant";
            }
        }
        output {
            leaf status {
                type rpcResult;
                description
                    "The status of the operation execution request.";
            }
            leaf status-detail {
                type string;
                description
                    "The detailed status of the operation execution request.";
            }
            leaf subject-name {
                type string;
                description
                    "The subject name of the installed certificate.";
            }
            leaf issuer-name {
                type string;
                description
                    "The subject name of the installed certificate.";
            }
        }
    }
    rpc crypto-host-generate-csr {
        description "Generate Host certificate signing request";
        input {
            leaf cert-path {
                mandatory true;
                description "Local file uri.";
                //type filename-uri-type;
                type string;
            }
            leaf key-path {
                mandatory true;
                description "Local key file uri.";
                //type filename-uri-type;
                type string;
            }
            leaf password {
                description "Password if key file is protected.";
                type string;
            }
            leaf common-name {
                description "Common name";
                type string;
            }
            leaf subj-alt-name {
                description "Subject Alternative Name";
                type string;
            }
            leaf email {
                description "Email";
                type string;
            }
            leaf org-name {
                description "Organization Name";
                type string;
            }
            leaf org-unit-name {
                description "Organizational Unit Name";
                type string;
            }
            leaf locality-name {
                description "Locality Name";
                type string;
            }
            leaf state-name {
                description "State or Province Name";
                type string;
            }
            leaf country-name {
                description "Country Name";
                type string;
            }
            leaf key-length {
                description "Key length";
                type uint32;
            }
        }
        output {
            leaf status {
                type rpcResult;
                description
                    "The status of the operation execution request.";
            }
            leaf status-detail {
                type string;
                description
                    "The detailed status of the operation execution request.";
            }
        }
    }
    rpc crypto-host-cert-delete {
        description "Delete Host certificate";
        input {
            leaf file-name {
                description "Host Cert File name";
                type string;
            }
            leaf fips-cert {
                type boolean;
                default false;
                description "Specifies if the certificate is FIPS compliant";
            }
        }
        output {
            leaf status {
                type rpcResult;
                description
                    "The status of the operation execution request.";
            }

            leaf status-detail {
                type string;
                description
                    "The detailed status of the operation execution request.";
            }
        }
    }
    rpc crypto-ca-cert-display {
        description "Display host/CA Certificates";
        input {
            leaf file-name {
                description "Certiticate name to be displayed";
                type string;
            }
            leaf raw-file {
                description "Option to display raw PEM format certificate.";
                type boolean;
            }
        }
        output {
            leaf status {
                type rpcResult;
                description
                    "The status of the operation execution request.";
            }

            leaf status-detail {
                type string;
                description
                    "The detailed status of the operation execution request.";
            }
            leaf-list cert-details {
                type string;
                description
                    "The details of provided certificate.";
            }
            leaf-list filename {
                type string;
                description
                    "The filename of certificate";
            }
        }
    }

    rpc crypto-host-cert-display {
        description "Display host/CA Certificates";
        input {
            leaf file-name {
                description "Certiticate name to be displayed";
                type string;
            }
        }
        output {
            leaf status {
                type rpcResult;
                description
                    "The status of the operation execution request.";
            }

            leaf status-detail {
                type string;
                description
                    "The detailed status of the operation execution request.";
            }
            leaf-list cert-details {
                type string;
                description
                    "The details of provided certificate.";
            }
            leaf-list filename {
                type string;
                description
                    "The filename of certificate";
            }
            leaf-list fips-cert {
                type boolean;
                description "Indicates if the certificate is FIPS compliant.";
            }
        }
    }

    rpc crypto-cert-verify {
        input {
            leaf cert-name {
                type string;
                description
                    "The certificate name to be verified.";
            }
            leaf cert-type {
                type enumeration {
                    enum host {
                        description "Host Certificate";
                    }
                    enum ca {
                        description "CA Certificate";
                    }
                }
                description
                    "Type of certificate to verify";
            }
            leaf ca-name {
                type string;
                description
                    "The optional CA with which to verify the certificate against";
            }
        }
        output {
           leaf status {
                type rpcResult;
                description
                    "The status of the operation execution request.";
            }

            leaf status-detail {
                type string;
                description
                    "The detailed status of the operation execution request.";
            }
            leaf verify-output {
                type string;
                description
                    "The output of openssl verify command.";
            }
        }
    }

    rpc crypto-sshkey-gen {
        description "SSH key config parameters";
        input {
            leaf key {
                description "This specifies the type of key to generate";
                type string;
            }
            leaf key-length {
                description "This specifies the length of the key type. RSA 
                    supports key length 2048(default),3072 and 4096. ECDSA 
                    supports key length 256(default),384 and 512";
                type string;
            }
        }
        output {
            leaf status {
                type rpcResult;
                description
                    "The status code of the operation execution request. A 
                    non-zero value indicates a failure.";
            }

            leaf status-detail {
                type string;
                description
                    "The detailed status of the operation execution request.";
            }
        }
    }

    rpc get-crypto-sshkey {
        description "RPC for getting SSH public key.";

        input {
            leaf key {
                type string {
                    pattern "ecdsa|rsa";
                }
                description "This specifies the type of key to be displayed";
            }
        }

        output {
            leaf status {
                type rpcResult;
                description
                    "The status code of the operation execution request. A
                     non-zero value indicates a failure.";
            }

            leaf content {
                type string;
                description "SSH key data";
            }
        }
    }

}
