module sonic-ars {
  namespace "http://github.com/Azure/sonic-ars";
  prefix sn-ars;
  yang-version 1.1;

  import ietf-yang-types { 
    prefix "ietf-yang"; 
  }

  import ietf-inet-types { 
    prefix "ietf-inet"; 
  }

  import sonic-ars-common { 
    prefix "sonic-ars-cmn"; 
  }

  import sonic-extension {
      prefix sonic-ext;
  }

  import sonic-port {
      prefix "sonic-prt";
  }

  organization
    "SONiC";

  contact
    "SONiC";

  description
     "SONIC ARS Global YANG";

  revision 2023-11-27 {
    description
      "Added Yang definition for ARS feature.";
  }

/*
 * RPCs
*/
  rpc clear-nhg-statistics {
    description "RPC for clearing NHG statistics. Input can be:
      1. Single NHG ID
      2. All NHG IDs";

    input {
      leaf nhg-id {
       type union {
         type uint32;
         type string;
       }
       description
         "all or one nhgid as input";
     }
    }
  
    output {
      leaf status {
        type int32;
        description
          "The status of the operation execution request.";
      }
      leaf status-detail {
        type string;
        description
          "The detailed status of the operation execution request.";
      }
    }
  }

  container sonic-ars {  

    container ARS_PROFILE {
      description
        "ARS profile configuration Table.";

      list ARS_PROFILE_LIST {

        key "name";
        sonic-ext:custom-validation IsARSFeatureSupported;
        sonic-ext:custom-validation ARSProfileMinMaxFieldValidation;
        sonic-ext:custom-validation ValidateARSMaxProfiles;

        leaf name {
          type string;
          description
            "unique name for ARS profile";
          sonic-ext:custom-validation IsARSProfileFieldSupported;
        }

        leaf algo {
          type sonic-ars-cmn:ars-algo-type;
          default EWMA;
          description
            "ARS algorithm used for quality computation";
        }

        leaf sampling-interval {
          type uint8 {
            range "1..255";
          }
          default 16;
          description
            "Sampling interval in microseconds of data for quality 
            measure computation.";
          sonic-ext:custom-validation ValidateArsProfileSamplingIntvl;
        }

        leaf random-seed {
          type uint32 {
            range "0..16777214";
          }
          default 10;
          description
            "Random seed for adaptive routing and switching.";
        }

        leaf port-load-past {
          type boolean;
          default true;
          description
            "Enable past port load as the quality parameter. 
            This is the average egress bytes measured on a port";
        }

        leaf port-load-past-weight {
          type uint8 {
            range "1..16";
          }
          default 2;
          description
            "Weight attribute is used in EWMA calculations.Large weight 
            lowers the significance of instantaneous measure on the overall average.";
        }

        leaf port-load-future {
          type boolean;
          default true;
          description
            "Enable future port load as the quality parameter. 
            This is the average queued bytes measured on a port.";
        }

        leaf port-load-future-weight {
          type uint8 {
            range "1..16";
          }
          default 2;
          description
            "Weight attribute is used in EWMA calculations. Large weight 
            lowers the significance of instantaneous measure on the overall average.";
        }

        leaf port-load-current {
          type boolean;
          default false;
          description
            "Set port loading value to current sampled value, 
            when sampled value is less than the average.";
        }

        leaf port-load-exponent {
          type uint8 {
            range "1..16";
          }
          default 2;
          description
            "EWMA exponent used in port loading computation. Larger the exponent, 
            larger is the weight to previously computed port loading value.";
        }

        leaf quant-band-0-min {
          type uint16 {
            range "0..10000";
          }
          default 0;
          description
            "Minimum threshold used for quantization process in Mbps for band 0.";
        }

        leaf quant-band-0-max {
          type uint16 {
            range "0..10000";
          }
          default 0;
          description
            "Maximum threshold used for quantization process in Mbps for band 0.";
        }

        leaf quant-band-1-min {
          type uint16 {
            range "0..10000";
          }
          default 0;
          description
            "Minimum threshold used for quantization process in Mbps for band 1.";
        }

        leaf quant-band-1-max {
          type uint16 {
            range "0..10000";
          }
          default 0;
          description
            "Maximum threshold used for quantization process in Mbps for band 1.";
        }

        leaf quant-band-2-min {
          type uint16 {
            range "0..10000";
          }
          default 0;
          description
            "Minimum threshold used for quantization process in Mbps for band 2.";
        }

        leaf quant-band-2-max {
          type uint16 {
            range "0..10000";
          }
          default 0;
          description
            "Maximum threshold used for quantization process in Mbps for band 2.";
        }

        leaf quant-band-3-min {
          type uint16 {
            range "0..10000";
          }
          default 0;
          description
            "Minimum threshold used for quantization process in Mbps for band 3.";
        }

        leaf quant-band-3-max {
          type uint16 {
            range "0..10000";
          }
          default 0;
          description
            "Maximum threshold used for quantization process in Mbps for band 3.";
        }

        leaf quant-band-4-min {
          type uint16 {
            range "0..10000";
          }
          default 0;
          description
            "Minimum threshold used for quantization process in Mbps for band 4.";
        }

        leaf quant-band-4-max {
          type uint16 {
            range "0..10000";
          }
          default 0;
          description
            "Maximum threshold used for quantization process in Mbps for band 4.";
        }

        leaf quant-band-5-min {
          type uint16 {
            range "0..10000";
          }
          default 0;
          description
            "Minimum threshold used for quantization process in Mbps for band 5.";
        }

        leaf quant-band-5-max {
          type uint16 {
            range "0..10000";
          }
          default 0;
          description
            "Maximum threshold used for quantization process in Mbps for band 5.";
        }

        leaf quant-band-6-min {
          type uint16 {
            range "0..10000";
          }
          default 0;
          description
            "Minimum threshold used for quantization process in Mbps for band 6.";
        }

        leaf quant-band-6-max {
          type uint16 {
            range "0..10000";
          }
          default 0;
          description
            "Maximum threshold used for quantization process in Mbps for band 6.";
        }

        leaf quant-band-7-min {
          type uint16 {
            range "0..10000";
          }
          default 0;
          description
            "Minimum threshold used for quantization process in Mbps for band 7.";
        }

        leaf quant-band-7-max {
          type uint16 {
            range "0..10000";
          }
          default 0;
          description
            "Maximum threshold used for quantization process in Mbps for band 7.";
        }

        leaf load-past-min-val {
          type uint32 {
            range "0..10000";
          }
          default 3000;
          description
            "Minimum past load threshold value for the quantization process.";
        }

        leaf load-past-max-val {
          type uint32 {
            range "0..10000";
          }
           default 6000;
           description
             "Maximum past load threshold value for the quantization process.";
        }

        leaf load-future-min-val {
          type uint32 {
            range "0..266338303";
          }
          default 2097152;
          description
            "Minimum future load threshold value for the quantization process.";
        }

        leaf load-future-max-val {
          type uint32 {
            range "0..266338303";
          }
          default 12582912;
          description
            "Maximum future load threshold value for the quantization process.";
          sonic-ext:custom-validation ValidateArsProfileLoadFutureMaxVal;
        }

        leaf load-current-min-val {
          type uint32 {
            range "0..133169151";
          }
          default 1048576;
          description
            "Minimum current load threshold value for the quantization process.";
        }

        leaf load-current-max-val {
          type uint32 {
            range "0..133169151";
          }
          default 6291456;
          description
            "Maximum current load threshold value for the quantization process.";
          sonic-ext:custom-validation ValidateArsProfileLoadCurrentMaxVal;
        }
      } //ARS_PROFILE_LIST
    } //ARS_PROFILE

    container ARS_SWITCH_BIND {
      description
        "ARS profile and object bind configurations in Switch Bind DB.";

      list ARS_SWITCH_BIND_LIST {

        key "name";
        sonic-ext:custom-validation IsARSFeatureSupported;

        leaf name {
          type sonic-ars-cmn:ars-bind-info;
          description
            "unique name for ARS profile bind";
          sonic-ext:custom-validation ValidateArsProfileBindDelete;
        }

        leaf profile {
          type leafref {
            path "/sn-ars:sonic-ars/sn-ars:ARS_PROFILE/sn-ars:ARS_PROFILE_LIST/sn-ars:name";
          }
          description
            "unique name for ARS profile to bind to switch";
        }

      } //ARS_SWITCH_BIND_LIST
    } //ARS_SWITCH_BIND

    container ARS_PORT_PROFILE {
      description
        "ARS Port Profile configuration table.";

      list ARS_PORT_PROFILE_LIST {

        key "name";
        sonic-ext:custom-validation IsARSFeatureSupported;
        sonic-ext:custom-validation ValidateArsPortProfileLoadWeight;

        leaf name {
          type string;
          description
            "unique name for ARS port profile";
          sonic-ext:custom-validation IsARSPortProfileFieldSupported;
        }

        leaf enable {
          type boolean;
          default false;
          description
            "Enable ARS for the port";
        }

        leaf load-scaling-factor {
          type sonic-ars-cmn:ars-port-load-factor;
          default 0;
          description
            "Configure port load scaling factor.";
          sonic-ext:custom-validation ValidateArsPortProfileLoadfactor;
        }

        leaf load-past-enable {
          type boolean;
          default false;
          description
            "Enable historical or past port load quality measure in switch pipeline.";
        }

        leaf load-future-enable {
          type boolean;
          default false;
          description
            "Enable future load quality measure in switch pipeline.";
        }

        leaf alt-path {
          type boolean;
          default false;
          description
            "Port is part of alternate path set if true, else part of primary path set.";
        }

        leaf load-past-weight {
          type uint8 {
            range "0..100";
          }
          default 80;
          description
            "Assign weight in percent to past port load quality measure in switch pipeline.";
        }

        leaf load-future-weight {
          type uint8 {
            range "0..100";
          }
          default 10;
          description
            "Assign weight in percent to future port load quality measure in switch pipeline.";
        }

      } //ARS_PORT_PROFILE_LIST
    } //ARS_PORT_PROFILE

    container ARS_PORT_BIND {
      description
        "ARS port profile configurations in Port Bind DB.";

      list ARS_PORT_BIND_LIST {

        key "name";
        sonic-ext:custom-validation IsARSFeatureSupported;
        sonic-ext:dependent-on "ARS_SWITCH_BIND_LIST";

        must "count(../../ARS_SWITCH_BIND/ARS_SWITCH_BIND_LIST[name='SWITCH']) > 0" {
            error-message "Please bind ars profile for the switch to proceed.";
            error-app-tag ars-invalid;
        }

        leaf name {
          type leafref {
            path "/sonic-prt:sonic-port/sonic-prt:PORT/sonic-prt:PORT_LIST/sonic-prt:ifname";
          }
          description
            "Port Name";
        }

        leaf profile {
          type leafref {
            path "/sn-ars:sonic-ars/sn-ars:ARS_PORT_PROFILE/sn-ars:ARS_PORT_PROFILE_LIST/sn-ars:name";
          }
          description
            "unique name for ARS port profile to bind to port";
          sonic-ext:custom-validation ValidateArsPortLoadfactor;
        }

      } //ARS_PORT_BIND_LIST
    } //ARS_PORT_BIND    

    container ARS_OBJECT {
      description
        "Next Hop Group, NHG object configuration for ARS";

      list ARS_OBJECT_LIST {

        key "name";
        sonic-ext:custom-validation IsARSFeatureSupported;
        sonic-ext:custom-validation ValidateArsObjectIdleTimeMaxFlowsMode;

        leaf name {
          type string;
          description
            "unique name for ARS NHG object";
          sonic-ext:custom-validation IsARSObjectFieldSupported;
        }

        leaf idle-time {
          type uint16 {
            range "16..32767";
          }
          default 80;
          description
            "Idle duration in microseconds. 
            This duration is to classify a flow-let in a macro flow.";
        }

        leaf max-flows {
          type uint16 {
            range "1..32768";
          }
          default 256;
          description
            "Maximum number of flow, states, that can be maintained 
            per this ARS object.";
          sonic-ext:custom-validation ValidateArsObjectMaxFlows;
        }

        leaf mode {
          type sonic-ars-cmn:ars-nhg-mode-types;
          default ARS_MODE_FLOWLET_QUALITY;
          description
            "ARS path (re)assignment mode.";
          sonic-ext:custom-validation ValidateArsObjectMode;
        }

        leaf mon-enable {
          type boolean;
          default false;
          description
            "Enable ARS monitoring";
        }

        leaf sample-packet {
          type boolean;
          default false;
          description
            "Enable/Disable ARS Samplepacket session.";
        } 

        leaf primary-path-quality-threshold {
          type uint32;
          default 16;
          description
            "Quality threshold for least cost ARS paths. Crossing down the 
            threshold will result in using the non least cost sub optimal path.";
        }

        leaf alt-path {
          type boolean;
          default false;
          description
            "Next hop group member is part of alternate path set if enabled.";
        }

        leaf alt-path-cost {
          type uint32;
          default 0;
          description
            "Cost of switching over to non least cost ARS paths.";
        }

        leaf alt-path-bias {
          type uint32;
          default 0;
          description
            "Indicates the bias in favor of alternate path.";
        }

        leaf max-primary-members {
          type uint32;
          default 16;
          description
            "Maximum number of primary members per adaptive routing group.";
        }

        leaf max-alt-members {
          type uint32;
          default 16;
          description
            "Maximum number of alternate members per adaptive routing group.";
        }
      } //ARS_OBJECT_LIST
    } //ARS_OBJECT

  } //sonic-ars
}
