module sonic-portchannel-interface {
    namespace "http://github.com/Azure/sonic-portchannel-interface";
    prefix spchint;
    yang-version 1.1;

    import ietf-inet-types {
        prefix inet;
    }

    import sonic-portchannel {
        prefix spc;
    }

    import sonic-vrf {
        prefix vrf;
    }

    import sonic-loopback-interface {
        prefix lointf;
    }

    import sonic-loopback {
        prefix lo;
    }

    import sonic-common {
        prefix cmn;
    }

    import sonic-interface-common {
        prefix sonic-if-cmn;
    }

    import sonic-extension {
        prefix sonic-ext;
    }

    organization
        "SONiC";

    contact
        "SONiC";

    description
        "SONIC PORTCHANNEL INTERFACE";

    revision 2022-12-21 {
        description
            "Add custom validation for vrf_name.";
    }

    revision 2020-07-26 {
        description
            "Change for sonic-loopback.yang.";
    }
    revision 2020-04-07 {
        description
            "Add VRF and IP address attribute";
    }
    revision 2020-02-28 {
        description
            "Add DHCP server attribute";
    }
    revision 2020-02-15 {
        description
            "Add ipv6_use_link_local_only attribute to interface object.";
    }
    revision 2019-12-01 {
        description
            "Add vrf_name for VRF interface binding.";
    }
    revision 2019-07-02 {
        description
            "Initial revision.";
    }


    container sonic-portchannel-interface {

        container PORTCHANNEL_INTERFACE {

            list PORTCHANNEL_INTERFACE_LIST {
                key "pch_name";
                sonic-ext:custom-validation ValidateVlanMapIntf;
                sonic-ext:custom-validation ValidateL2ConfigExists;

                leaf pch_name{
                    type leafref {
                        path "/spc:sonic-portchannel/spc:PORTCHANNEL/spc:PORTCHANNEL_LIST/spc:name";
                    }
                }
                leaf nat_zone {
                    type uint8 {
                        range "0..3";
                    }
                    must "((/cmn:operation/cmn:operation != 'CREATE') and (/cmn:operation/cmn:operation != 'UPDATE')) or " +
                            "(count(/sonic-portchannel-interface/PORTCHANNEL_INTERFACE/PORTCHANNEL_INTERFACE_IPADDR_LIST[pch_name=current()/../pch_name]) > 1)"
                            {
                                    error-message "NAT zone can be configured on portchannel routing interface only";
                                    error-app-tag nat-invalid-portchannel-routing-interface;
                            }
                }

                leaf vrf_name {
                    type union {
                        type string {
                            pattern "mgmt";
                        }

                        type leafref {
                            path "/vrf:sonic-vrf/vrf:VRF/vrf:VRF_LIST/vrf:vrf_name";
                        }
                    }

                    sonic-ext:custom-validation ValidateIntfVrfBinding;
                }

                leaf-list dhcp_servers{
                    max-elements 16;
                    type inet:ip-address;
                }

                leaf-list dhcpv6_servers{
                      max-elements 16;
                      type inet:ipv6-address;
		}

                leaf dhcp_relay_link_select {
                      type cmn:mode-enable;
                      must "((/cmn:operation/cmn:operation != 'CREATE') and (/cmn:operation/cmn:operation != 'UPDATE')) or " +
                           "(current()/../dhcp_relay_src_intf)"
                            {
                                     error-message "DHCP relay source interface not configured or invalid operation";
                                     error-app-tag dhcp-server-adress-config;
                            }
                 }

                 leaf dhcp_relay_src_intf {
                       type string;
                       must "((/cmn:operation/cmn:operation != 'CREATE') and (/cmn:operation/cmn:operation != 'UPDATE')) or " +
                            "(current()/../dhcp_servers)"
                             {
                                      error-message "DHCP relay address not configured or invalid operation";
                                      error-app-tag dhcp-server-adress-config;
                             }

                 }

                 leaf dhcp_relay_max_hop_count {
                        type uint32;
                        must "((/cmn:operation/cmn:operation != 'CREATE') and (/cmn:operation/cmn:operation != 'UPDATE')) or " +
                               "(current()/../dhcp_servers)"
                                {
                                      error-message "DHCP relay address not configured";
                                      error-app-tag dhcp-server-adress-config;
                                }

                 }
                 leaf dhcp_server_vrf {
                         type union {
                             type string {
                                 pattern "mgmt";
                             }
                             type leafref {
                                 path "/vrf:sonic-vrf/vrf:VRF/vrf:VRF_LIST/vrf:vrf_name";
                             }
                         }
                         must "((/cmn:operation/cmn:operation != 'CREATE') and (/cmn:operation/cmn:operation != 'UPDATE')) or " +
                               "(current()/../dhcp_servers)"
                                {
                                      error-message "DHCP server not configured";
                                      error-app-tag dhcp-server-invalid-vrf-config;
                                }
                 }

                 leaf dhcp_relay_vrf_select {
                    type cmn:mode-enable;
                    must "((/cmn:operation/cmn:operation != 'CREATE') and (/cmn:operation/cmn:operation != 'UPDATE')) or " +
                            "(current()/../dhcp_servers)"
                       {
                               error-message "DHCP relay address not configured";
                               error-app-tag dhcp-server-adress-config;
                       }
                 }

                 leaf dhcp_relay_policy_action {
                    type cmn:relay-policy-action;
                    must "((/cmn:operation/cmn:operation != 'CREATE') and (/cmn:operation/cmn:operation != 'UPDATE')) or " +
                            "(current()/../dhcp_servers)"
                       {
                               error-message "DHCP relay address not configured";
                               error-app-tag dhcp-server-adress-config;
                       }
                 }

                leaf dhcp_relay_circuit_id_format {
                     type string;
                     must "((/cmn:operation/cmn:operation != 'CREATE') and (/cmn:operation/cmn:operation != 'UPDATE')) or " +
                            "(current()/../dhcp_servers)"
                     {
                         error-message "DHCP server not configured";
                         error-app-tag dhcp-server-address-config;
                     }
                }

                leaf dhcp_relay_smart_mode {
                     type cmn:mode-enable;
                     description "Enable/Disable smart relay mode on the portchannel interface.";
                     must "((/cmn:operation/cmn:operation != 'CREATE') and (/cmn:operation/cmn:operation != 'UPDATE')) or " +
                            "(current()/../dhcp_servers)"
                     {
                         error-message "DHCP server not configured";
                         error-app-tag dhcp-server-address-config;
                     }
                }

                leaf dhcpv6_relay_src_intf {
                         type string;
                         must "((/cmn:operation/cmn:operation != 'CREATE') and (/cmn:operation/cmn:operation != 'UPDATE')) or " +
                                "(current()/../dhcpv6_servers) "
                               {
                                         error-message "DHCP relay address not configured";
                                         error-app-tag dhcp-server-adress-config;
                               }

                }

                leaf dhcpv6_relay_max_hop_count {
                         type uint32;
                         must "((/cmn:operation/cmn:operation != 'CREATE') and (/cmn:operation/cmn:operation != 'UPDATE')) or " +
                               "(current()/../dhcpv6_servers) "
                               {
                                         error-message "DHCP relay address not configured";
                                         error-app-tag dhcp-server-adress-config;
                               }
                }

                 leaf dhcpv6_server_vrf {
                         type union {
                             type string {
                                 pattern "mgmt";
                             }
                             type leafref {
                                 path "/vrf:sonic-vrf/vrf:VRF/vrf:VRF_LIST/vrf:vrf_name";
                             }
                         }
                         must "((/cmn:operation/cmn:operation != 'CREATE') and (/cmn:operation/cmn:operation != 'UPDATE')) or " +
                                "(current()/../dhcpv6_servers)"
                               {
                                        error-message "DHCP server or src-intf not configured";
                                        error-app-tag dhcp-server-invalid-vrf-config;
                               }
                 }

                 leaf dhcpv6_relay_vrf_select {
                         type cmn:mode-enable;
                         must "((/cmn:operation/cmn:operation != 'CREATE') and (/cmn:operation/cmn:operation != 'UPDATE')) or " +
                               "(current()/../dhcpv6_servers) "
                               {
                                         error-message "DHCP relay address not configured";
                                         error-app-tag dhcp-server-adress-config;
                               }
                 }

                 leaf ipv6_autoconfig {
                         type cmn:mode-enable;
                         default disable;
                         sonic-ext:custom-validation ValidateNdProxyexists;
                         description
                               "Enable IPv6 stateless auto-configuration on interface";
                 }

                 leaf ipv6_dad {
                        type cmn:dad-mode;
                        default disable;
                          description
                               "Enable/Disable IPv6 DAD on the interface";
                 }

                leaf ipv6_use_link_local_only {
                    type cmn:mode-enable;
                    default disable;
                    description
                        "Enable IPv6 link local address on interface";
                }

                leaf unnumbered {
					must "((/cmn:operation/cmn:operation != 'CREATE') and (/cmn:operation/cmn:operation != 'UPDATE')) or " +
						 "not(contains(/sonic-portchannel-interface/PORTCHANNEL_INTERFACE/PORTCHANNEL_INTERFACE_IPADDR_LIST[pch_name=current()/../pch_name]/ip_prefix, '.'))"
					{
						error-message "Cannot configure IP address and IP Unnumbered interface configurations on the same interface";
						error-app-tag pointf-ip-config;
					}


                    sonic-ext:custom-validation ValidateIpv4UnnumIntf;
                    sonic-ext:custom-validation ValidateUnnumVrfMatch;

                    type leafref {
                        path "/lo:sonic-loopback/lo:LOOPBACK/lo:LOOPBACK_LIST/lo:name";
                    }
                }

                leaf-list helper_addresses {
                    type sonic-if-cmn:vrf-ip;
                    max-elements 4;
                    description
                        "List of destination addresses with each being a combination of Vrf and IP address";
                    must "((/cmn:operation/cmn:operation != 'CREATE') and (/cmn:operation/cmn:operation != 'UPDATE')) or " +
                            "(count(/sonic-portchannel-interface/PORTCHANNEL_INTERFACE/PORTCHANNEL_INTERFACE_IPADDR_LIST[pch_name=current()/../pch_name]) > 1)"
                            {
                                    error-message "Helper address can be configured on portchannel routing interface only";
                                    error-app-tag helper-address-invalid-portchannel-routing-interface;
                            }
                }

                leaf proxy_arp {
                    type cmn:proxy-mode;
                    sonic-ext:custom-validation ValidateIpv4ProxyArpIntf;
                    description
                        "Proxy-ARP config modes";
                }
                leaf nd_proxy {
                    type cmn:proxy-mode;
                    sonic-ext:custom-validation ValidateIpv6NdProxyIntf;
                    description
                        "ND-Proxy config modes";
                }
                leaf-list nd_proxy_rules {
                     type inet:ipv6-prefix;
                     sonic-ext:custom-validation ValidateIpv6NdProxyRules;
                     description
                        "Configuring the IPv6 prefixes for nd-proxy rules";
                }
            }

            list PORTCHANNEL_INTERFACE_IPADDR_LIST {
                key "pch_name ip_prefix";

				must "(/cmn:operation/cmn:operation != 'CREATE') or " +
					 "(not(contains(current()/ip_prefix, '.')) or "  +
					 "(count(current()/../PORTCHANNEL_INTERFACE_LIST[pch_name=current()/pch_name]/unnumbered) = 0))"
				{
					error-message "Cannot configure IPv4 address and IP Unnumbered interface configurations on the same interface";
					error-app-tag pointf-unnum;
				}

                leaf pch_name{
                    type leafref {
                        path "../../PORTCHANNEL_INTERFACE_LIST/pch_name";
                    }
                }

                leaf eui64 {
                    type cmn:mode-enable;
                    default disable;
                    description
                       "Controls the IPv6 Eui-64 identifier flag";
                }

                leaf ip_prefix {
                    type inet:ip-prefix;
                    sonic-ext:custom-validation ValidateIntfIp;

                }
                leaf secondary {
                    type boolean;
                }
            }
        }
    }
}
