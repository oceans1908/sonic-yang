module sonic-system-ldap {
  namespace "http://github.com/Azure/sonic-system-ldap";
  prefix ssys-ldap;
  yang-version 1.1;

  import ietf-inet-types {
      prefix inet;
  }

  import sonic-pki {
    prefix spki;
  }

  import sonic-port {
      prefix sport;
  }

  import sonic-portchannel {
      prefix spc;
  }

  import sonic-vlan {
      prefix svlan;
  }

  import sonic-loopback {
      prefix lo;
  }

  import sonic-mgmt-port {
      prefix smgmt;
  }

  import sonic-interface {
      prefix subif;
  }

  import sonic-vrf {
      prefix vrf;
  }

  import sonic-extension {
      prefix sonic-ext;
  }

  organization
      "SONiC";

  contact
      "SONiC";

  description
      "SONiC LDAP";

  revision 2024-08-08 {
      description "LDAP security profile.";
  }

  revision 2020-08-28 {
      description "LDAP vrf syntax.";
  }

  revision 2020-07-26 {
      description
          "Change for sonic-loopback.yang.";
  }

  revision 2020-05-14 {
      description
          "Initial revision.";
  }
  
  typedef ldap_ssl_type {
    type enumeration {
      enum on {
        description
          "LDAP over SSL/TLS";
      }
      enum off {
        description
          "No SSL/TLS";        
      }
      enum start_tls {
        description
          "Use StartTLS instead of raw LDAP over SSL/TLS";
      }        
    }
    description
      "LDAP Server TLS Configuration types";
   }

  typedef ldap_maps_type {
    type enumeration {
      enum ATTRIBUTE;
      enum OBJECTCLASS;
      enum DEFAULT_ATTRIBUTE_VALUE;
      enum OVERRIDE_ATTRIBUTE_VALUE;
      enum CUSTOM_SONIC_ROLES_ATTRIBUTE_VALUE;
    }
    description
      "LDAP server map names";
   }

  container sonic-system-ldap {

    container LDAP {

      list LDAP_LIST {

        key "ldap_type";

        leaf ldap_type {
            type enumeration {
                enum global;
                enum nss;
                enum sudo;
                enum pam;
            }
            description
							"LDAP global type";
        }
        
				leaf timelimit {
					type uint32;
		      description
		        "Search time limit of the LDAP server";
				}
		
				leaf bind_timelimit {
					type uint32;
		      description
    		    "Connect time limit of the LDAP server";      
				}
				
				leaf idle_timelimit {
					when "current()/../ldap_type = 'global' or current()/../ldap_type = 'nss'";				
					type uint32;
				}
				
				leaf retry {
					type uint8  {
						range "0..10" {
							error-message "Retry attempt must be 0 to 10";
						}
					}
		      description
		        "Number of retransmit attempt by LDAP server";										
				}
				
				leaf port {
					type inet:port-number;
		      description
		        "LDAP server port";
				}
				
				leaf scope {
				  when "current()/../ldap_type = 'global' or current()/../ldap_type = 'nss' or current()/../ldap_type = 'pam'";
		      type enumeration {
		        enum sub {
		          description
		            "sub";
		        }
		        enum one {
		          description
		            "one";        
		        }
		        enum base {
		          description
		            "base";                
		        }        
		      }
		      description
		        "LDAP search scope";
				}
				
				leaf ldap_version {
					type uint8  {
						range "2..3" {
							error-message "LDAP version must be 2 to 3";
						}						
					}
		      description
		        "LDAP server protocol version";
				}
				
				leaf base {
					type string;
		      description
		        "Base Distinguished Name to use for searches";
				}
				
				leaf ssl {
					type ldap_ssl_type;
		      description
		        "TLS configuration of the LDAP server";
				}
				
				leaf binddn {
					type string;
		      description
		        "Distinguished name with which to bind to the LDAP server. The
		         default is to bind anonymously.";
				}
				
				leaf bindpw {
                                        sonic-ext:custom-validation ValidateEncryptedKey;
					type string {
					      length "1..65";
					      pattern "[^ ]*" {
						  error-message 'Invalid bind password (Valid chars are ASCII printable except SPACE)';
						  error-app-tag ldap-invalid-bindpw-value;
					      }
					}
		      description
		        "Credentials with which to bind to the LDAP server. Only used with
		         bind-dn.";
				}
				
				leaf pam_filter {
				  when "current()/../ldap_type = 'global' or current()/../ldap_type = 'pam'";				  
					type string;
		      description
		        "LDAP PAM filter to use when retrieving user information.";
				}
				
				leaf pam_login_attribute {
				  when "current()/../ldap_type = 'global' or current()/../ldap_type = 'pam'";
					type string;
		      description
		        "LDAP PAM Login attribute to use when constructing the attribute
		         value assertion for retrieving a directory entry for user's
		         login name";
				}
				
				leaf pam_group_dn {
				  when "current()/../ldap_type = 'global' or current()/../ldap_type = 'pam'";
					type string;
		      description
		        "LDAP PAM Group Distinguished name of a group to which a user
		         must belong for logon authorization to succeed. Only used
		         when aaa authorization for ldap is configured.";
				}
				
				leaf pam_member_attribute {
				  when "current()/../ldap_type = 'global' or current()/../ldap_type = 'pam'";
					type string;
		      description
		        "LDAP PAM Member attribute to use when testing a user's
		         membership of a group specified in the ldap-pam-group-dn. Only
		         used when aaa authorization for ldap is configured.";
				}
				
				leaf sudoers_base {
				  when "current()/../ldap_type = 'global' or current()/../ldap_type = 'sudo'";
					type string;
		      description
		        "Base DN to use when performing sudo LDAP queries";
				}

				leaf sudoers_search_filter {
				  when "current()/../ldap_type = 'global' or current()/../ldap_type = 'sudo'";
					type string;
		      description
		        "Sudoers Search Filter to use when performing sudo LDAP queries";
				}
				
				leaf nss_base_passwd {
				  when "current()/../ldap_type = 'global' or current()/../ldap_type = 'nss' or current()/../ldap_type = 'pam'";
					type string;
		      description
		        "LDAP NSS search base for passwd map";					
				}
				
				leaf nss_base_group {
				  when "current()/../ldap_type = 'global' or current()/../ldap_type = 'nss'";
					type string;
		      description
		        "LDAP NSS search base for group map";
				}
				
				leaf nss_base_shadow {
				  when "current()/../ldap_type = 'global' or current()/../ldap_type = 'nss'";
					type string;
		      description
		        "LDAP NSS search base for shadow map";
				}
				
				leaf nss_base_netgroup {
				  when "current()/../ldap_type = 'global' or current()/../ldap_type = 'nss'";
					type string;
		      description
    		    "LDAP NSS search base for netgroup map";
				}
				
				leaf nss_base_sudoers {
				  when "current()/../ldap_type = 'global' or current()/../ldap_type = 'nss'";
					type string;
		      description
		        "LDAP NSS search base for sudoers map";
				}
				
				leaf nss_initgroups_ignoreusers {
				  when "current()/../ldap_type = 'global' or current()/../ldap_type = 'nss'";
					type string;
		      description
		        "LDAP NSS init groups ignore users";
				}

				leaf nss_skipmembers {
				  when "current()/../ldap_type = 'global' or current()/../ldap_type = 'nss'";
                                        type boolean;
		      description
		        "LDAP NSS skip members ";
				}

                leaf security_profile {
                    type leafref {
                        path "/spki:sonic-pki/spki:SECURITY_PROFILES/spki:SECURITY_PROFILES_LIST/spki:profile-name";
                    }
                    sonic-ext:custom-validation ValidateSecurityProfile;
                }
				
                leaf src_intf {
                    type union {
                        type leafref {
                            path "/sport:sonic-port/sport:PORT/sport:PORT_LIST/sport:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/lo:sonic-loopback/lo:LOOPBACK/lo:LOOPBACK_LIST/lo:name";
                        }
                        type leafref {
                            path "/smgmt:sonic-mgmt-port/smgmt:MGMT_PORT/smgmt:MGMT_PORT_LIST/smgmt:ifname";
                        }
                        type leafref {
                            path "/subif:sonic-interface/subif:VLAN_SUB_INTERFACE/subif:VLAN_SUB_INTERFACE_LIST/subif:id";
                        }
                    }
                }
				
                leaf vrf_name {
                    type union {
                        type enumeration{
                            enum mgmt;
                        }
                        type leafref {
                            path "/vrf:sonic-vrf/vrf:VRF/vrf:VRF_LIST/vrf:vrf_name";
                       }
                    }
                    description
                   "Vrf name";
                }
      }
  	}

    container LDAP_SERVER {

      list LDAP_SERVER_LIST {
        key "name";

        leaf name {
        		type inet:host;
                        sonic-ext:custom-validation ValidateIPAddressOrHostname;
            description
							"LDAP server's Domain name or IP address (IPv4 or IPv6)";            
        }

        leaf port {
            type inet:port-number;
            description
              "Server port number";
        }

				leaf use_type {
		      type enumeration {
		        enum all {
		          description
		            "all";
		        }
		        enum nss {
		          description
		            "nss";        
		        }
		        enum sudo {
		          description
		            "sudo";                
		        }
		        enum pam {
		          description
		            "sudo";                
		        }                
		        enum nss_sudo {
		          description
		            "nss, sudo";                
		        }
		        enum nss_pam {
		          description
		            "nss, pam";                
		        }
		        enum sudo_pam {
		          description
		            "sudo, pam";                
		        }	        
		      }		      
					description
						"Server type";			
				}
				
				leaf priority {
					type uint8  {
						range "1..99" {
							error-message "LDAP server priority must be 1 to 99";
						}						
					}
					description
						"Server priority";			
				}
				
				leaf ssl {
					type ldap_ssl_type;				
		 			description
						"Server TLS";			
				}
				
				leaf retry {
					type uint8  {
						range "0..10" {
							error-message "Retry attempt must be 0 to 10";
						}						
					}
					description
						"Retransmit attempt";			
				}
      }
    }

    container LDAP_MAP {
      list LDAP_MAP_LIST {
        key "name from";

        leaf name {
        	type ldap_maps_type;
					description
						"LDAP map name";
				}

        leaf from {
        	type string;
					description
						"LDAP map key";
				}
				
				leaf to {
					type string;
                                        sonic-ext:custom-validation ValidateRBACRole;
					mandatory true;
					description
						"LDAP map value";
				}    
  		}
  	}
  }  	
}
