module openconfig-infra-logging {
    yang-version "1";

    namespace "http://openconfig.net/yang/system/infra-logging/extension";

    prefix "oc-infra-logging";

  // import some basic types
  import openconfig-extensions { prefix oc-ext; }

  import openconfig-system-ext { prefix oc-sys-ext; }

  // meta
  organization
    "SONiC";

  contact
    "SONiC";

  description
    "This module contains a collection of YANG definitions for system log component";

  revision "2024-03-17" {
    description
      "Add rpc for auditd system support.";
     reference "0.2.0";
  }

  revision "2021-09-15" {
    description
      "Initial draft revision.";
     reference "0.1.0";
  }

  oc-ext:openconfig-version "0.1.0";

  // typedef statements


  // grouping statements



    rpc show-sys-log {
        description
            "show system log";
        input {
            leaf num-lines{
                type uint16{
                    range "1..65535" {
                        error-message "NUM Lines out of range 1..65535";
                    }
                }
               description
                    "output the last NUM lines of system log";
            }
            leaf since{
               type string;
               description
                    "Show logs since a given date";
            }
            leaf loglevel{
               type string;
               description
                    "Show logs in a given severity and higher";
            }
            leaf logtype{
               type string;
               description
                    "Log types: all inmem syslog";
            }
            leaf severity{
               type string;
               description
                    "Show logs with given severity";
            }

        }

        output {
            leaf-list status-detail{
               type string;
               description
                    "The detailed status of the operation execution request.";
           }
        }
    }

    rpc show-memory-hist {
        description
            "show memory histogram";
        input {
            leaf input-str{
               type string;
               description
                    "type of memory histogram";
            }
        }

        output {
            leaf status-detail{
               type string;
               description
                    "The detailed status of the operation execution request.";
           }
        }
    }
    rpc clear-sys-log {
        description
            "clear logging";
        output {
            leaf result{
               type string;
               description
                    "The detailed status of the operation execution request.";
           }
        }
    }

    rpc sys-log-count {
        description
            "total number of system log entries";
        output {
            leaf result{
               type string;
               description
                    "total number of system log entries";
           }
        }
    }
    rpc set-loglevel-severity {
        description
            "logging severity level setting";
        input {
            leaf loglevel{
                type string; 
                description
                    "loglevel value";
            }
            leaf component-name {
                type string; 
                description
                    "component name in DB for which loglevel is applied (provided with loglevel): component name or all";
            }
            leaf sai-component {
                type boolean; 
                default false;
                description
                    "apply loglevel for SAI api component";
            }
        }
        output {
            leaf-list status-detail{
               type string;
               description
                    "The detailed status of the operation execution request.";
           }
        }
    }
    rpc get-loglevel-severity {
        description
           "print components registered in DB for which setting can be applied";
        output {
            leaf-list status-detail{
               type string;
               description
                    "The detailed status of the operation execution request.";
           }
        }
    }
    rpc show-sys-in-memory-log {
        description
            "show system inmemory log";
        input {
            leaf num-lines{
                type uint16{
                    range "1..65535" {
                        error-message "NUM Lines out of range 1..65535";
                    }
                }
               description
                    "output the last NUM lines of system inmemory log";
            }
        }

        output {
            leaf-list status-detail{
               type string;
               description
                    "The detailed status of the operation execution request.";
           }
        }
    }
    rpc sys-in-memory-log-count {
        description
            "total number of system inmemory log entries";
        output {
            leaf result{
               type string;
               description
                    "total number of system inmemory log entries";
           }
        }
    }

   rpc logger {
        description
            "enter messages into the system log";
        input {
            leaf messages {
               type string; 
               description
                    "messages into the system log";
            }
        }

        output {
            leaf result{
               type string;
               description
                    "The detailed status of the operation execution request.";
           }
        }
    }

    rpc reboot-ops{
        description
            "Switch boot operations:
                - reboot: reboot operation
                - warm-reboot : warm reboot  operation
                - fast-reboot : fast reboot operation
            The result of the requested command is sent as a string.";
        input {
            leaf param {
               type string;
               description
                    "reboot options";
            }
        }
        output {
            leaf result {
                type string;
                description
                    "String showing the result of the last requested command (reboot, warm-reboot or fast-reboot).";
            }
        }
    }


    rpc show-auditd-system-log {
        description
            "show auditd system log";
        input {
            leaf content-type {
               type enumeration {
                    enum BRIEF {
                        description "Get the last few lines of code as defined by the system.";
                    }
                    enum ALL {
                        description "Get all the log from the system.";
                    }
               }
               default "BRIEF";
               description "Indicates the log size to be retrieved.";
           }
        }

        output {
            list auditd-system-log {
               leaf content {
                    type string;
                    description "Auditd system log";
                }
            }
        }
    }

    rpc show-auditd-system-rules {
        description "Get auditd system rules";
    
        output {
            leaf-list status-detail{
                type string;
                description
                    "The detailed status of the operation execution request.";
           }        
       }
    }  
}
