module sonic-system-radius {
    namespace "http://github.com/Azure/sonic-system-radius";
    prefix ssys;
    yang-version 1.1;

    import ietf-inet-types {
        prefix inet;
    }

    import sonic-extension {
        prefix sonic-ext;
    }

    import sonic-port {
        prefix prt;
    }

    import sonic-portchannel {
        prefix spc;
    }

    import sonic-vlan {
        prefix svlan;
    }

    import sonic-loopback {
        prefix lo;
    }

    import sonic-mgmt-port {
        prefix smt;
    }

    import sonic-interface {
        prefix subif;
    }

    import sonic-vrf {
        prefix vrf;
    }

    import sonic-pki {
        prefix spki;
    }

    organization
        "SONiC";

    contact
        "SONiC";

    description
        "SONiC RADIUS";

    revision 2024-09-10 {
        description "Add RADIUS over TLS attributes.";
    }

    revision 2020-08-28 {
        description "RADIUS vrf syntax.";
    }

    revision 2020-07-26 {
        description "Change for sonic-loopback.yang.";
    }

    revision 2020-06-30 {
        description "RADIUS source-interface.";
    }

    revision 2020-05-24 {
        description "RADIUS statistics.";
    }

    revision 2020-05-02 {
        description "Allowed domain name as well for server configuration.";
    }

    revision 2020-03-30 {
        description "NAS-IP|IPV4-Address attribute.";
    }

    revision 2020-02-17 {
        description "Allow special characters in passkey.";
    }

    revision 2019-11-14 {
        description
            "Initial revision.";
    }

    container sonic-system-radius {

        container RADIUS {

            list RADIUS_LIST {

                key "global_key";

                leaf global_key {
                    type enumeration {
                        enum global;
                    }
                    description
                            "RADIUS global key";
                }

                leaf passkey {
                    sonic-ext:custom-validation ValidateEncryptedKey;
                    type string;
                    description
                            'RADIUS global shared secret';
                }

                leaf auth_type {
                    default "pap";
                    type enumeration {
                        enum pap;
                        enum chap;
                        enum mschapv2;
                    }
                    description
                            "RADIUS global method used for authenticating the comm. mesg.";
                }

                leaf src_ip {
                    type inet:ip-address;
                    description
                            "source IP address (IPv4 or IPv6) for the outgoing RADIUS pkts.";
                }

                leaf nas_ip {
                    type inet:ip-address;
                    description
                            "NAS-IP|IPV6-Address attribute for the outgoing RADIUS pkts.";
                }

                leaf statistics {
                    type boolean;
                    description
                            "Should statistics collection be enabled/disabled";
                }

                leaf timeout {
                    default 5;
                    type uint16 {
                        range "1..60" {
                            error-message "RADIUS timeout must be 1..60";
                        }
                    }
                }

                leaf retransmit {
                    default 3;
                    type uint8 {
                        range "0..10" {
                            error-message "RADIUS retransmit must be 0..10";
                        }
                    }
                }
            }
        }

        container RADIUS_SERVER {

            list RADIUS_SERVER_LIST {
                key "ipaddress";

                max-elements 8;

                leaf ipaddress {
                    type inet:host;
                    sonic-ext:custom-validation ValidateIPAddressOrHostname;
                    description
                        "RADIUS server's Domain name or IP address (IPv4 or IPv6)";
                }

                leaf auth_port {
                    default 1812;
                    type inet:port-number;
                }

                leaf passkey {
                    sonic-ext:custom-validation ValidateEncryptedKey;
                    type string;
                    description
                            'RADIUS servers shared secret';
                }

                leaf auth_type {
                    default "pap";
                    type enumeration {
                        enum pap;
                        enum chap;
                        enum mschapv2;
                    }
                    description
                            "RADIUS server's method used for authenticating the comm. mesg.";
                }

                leaf priority {
                    type uint8 {
                        range "1..64" {
                            error-message "RADIUS priority must be 1..64";
                        }
                    }
                    description
                            "RADIUS server's priority";
                }

                leaf timeout {
                    default 5;
                    type uint16 {
                        range "1..60" {
                            error-message "RADIUS timeout must be 1..60";
                        }
                    }
                }

                leaf retransmit {
                    default 3;
                    type uint8 {
                        range "0..10" {
                            error-message "RADIUS retransmit must be 0..10";
                        }
                    }
                }

                leaf vrf {
                    type union {
                        type enumeration{
                            enum mgmt;
                        }
                        type leafref {
                            path "/vrf:sonic-vrf/vrf:VRF/vrf:VRF_LIST/vrf:vrf_name";
                       }
                    }
                    description
                            "RADIUS server's VRF";
                }

                leaf src_intf {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/lo:sonic-loopback/lo:LOOPBACK/lo:LOOPBACK_LIST/lo:name";
                        }
                        type leafref {
                            path "/smt:sonic-mgmt-port/smt:MGMT_PORT/smt:MGMT_PORT_LIST/smt:ifname";
                        }
                        type leafref {
                            path "/subif:sonic-interface/subif:VLAN_SUB_INTERFACE/subif:VLAN_SUB_INTERFACE_LIST/subif:id";
                        }
                    }
                }

                leaf protocol {
                    type enumeration {
                        enum UDP;
                        enum TLS;
                    }
                    default UDP;
                    description
                        "Radius server protocol";
                }

                leaf security_profile {
                    type leafref {
                        path "/spki:sonic-pki/spki:SECURITY_PROFILES/spki:SECURITY_PROFILES_LIST/spki:profile-name";
                    }
                    must "current()/../protocol = 'TLS'" {
                        error-message "Security profile can only be configured for TLS protocol. Default protocol is UDP";
                    }
                    sonic-ext:custom-validation ValidateProtocolType;
                    sonic-ext:custom-validation ValidateSecurityProfile;
                    sonic-ext:custom-validation ValidateCertificatePresence;
                    description
                        "Name of the security profile associated";
                }
            }
        }

        container RADIUS_SERVER_STATS {
            sonic-ext:db-name "COUNTERS_DB";
            sonic-ext:key-delim ":";

            config false;
            description "Counters DB RADIUS server statistics";

            list RADIUS_SERVER_STATS_LIST {
                key "ipaddress";

                max-elements 8;

                leaf ipaddress {
                    type inet:host;
                    description
                        "RADIUS server's Domain name or IP address (IPv4 or IPv6)";
                }

                leaf access_requests {
                    type uint64;
                    description "Sent Access Requests";
                }

                leaf access_accepts {
                    type uint64;
                    description "Received Access Accepts";
                }

                leaf access_rejects {
                    type uint64;
                    description "Received Access Rejects";
                }

                leaf access_challenges {
                    type uint64;
                    description "Received Access Challenges";
                }

                leaf retried_access_requests {
                    type uint64;
                    description "Retried Access Requests";
                }

                leaf bad_authenticators {
                    type uint64;
                    description "Bad Authenticators";
                }

                leaf invalid_packets {
                    type uint64;
                    description "Invalid Packets";
                }
            }
        }
    }
}
