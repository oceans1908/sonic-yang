module sonic-config-mgmt {
  namespace "http://github.com/Azure/sonic-config-mgmt";
  prefix scm;

  import sonic-port {
    prefix prt;
  }

  import sonic-common {
    prefix scommon;
  }

  import sonic-extension {
    prefix sonic-ext;
  }

  organization
    "SONiC";
  contact
    "SONiC";
  description
    "SONIC Configuration Management";

  revision 2019-09-15 {
    description
      "Initial revision.";
  }


  container sonic-config-mgmt {
    description "Switch configuration management";

    container DEFAULT_CONFIG_PROFILES {
      description "STATE_DB table which provides the list of supported default configuration profiles";
      config false;
      list DEFAULT_CONFIG_PROFILES_LIST {
         key "profile-name";
         leaf profile-name {
             description
               "Name of factory default configuration profile name.";
             type string;
         }
         leaf description {
             description
               "A textual description of the default configuration profile.";
             type string;
        }
         leaf active {
             description
               "Indicates if the default configuration profile is being used as the
               switch factory default configuration profile.";
             type boolean;
         }
      }
    }
    container CFG_RELOAD {
      sonic-ext:db-name "STATE_DB";
      config false;
      description "State data";

      list CFG_RELOAD_LIST {
         key "name";
         max-elements 1;

         leaf name{
             type enumeration {
                enum state;
             }
             description
                "table key";
         }

         leaf cfg_reload_state{
             description
               "Config Reload state";
             type string;
        }
        leaf cfg_reload_state_detail {
             description
               "Config Reload state description";
             type string;
        }
         leaf cfg_reload_start_time{
             description
               "Config Reload start time.
                 Timestamp value is expressed as number of secods elapsed since the
                 unix epoch (Jan 1, 1970 00:00:00 UTC).";
             type scommon:timeticks64;

        }
         leaf cfg_reload_end_time{
             description
               "Config Reload end time.
                Timestamp value is expressed as number of secods elapsed since the
                unix epoch (Jan 1, 1970 00:00:00 UTC).";
             type scommon:timeticks64;
        }
      }
    }

  }

  rpc write-erase {
      description
          "Configuration Erase Features:
             - op_write_erase : Erase configuration files except for the management interface configuration.
             - op_write_erase_boot : Erase the configuration files including the management interface configuration.
             - op_write_erase_install : Restore SONiC switch content to default values.
             - op_no_write_erase : Cancel configuration erase operation.

           The detailed result of the requested command is sent as a string.";
      input {
          leaf subcmd {
              type string;
              description "Subcommand: op_write_erase | op_write_erase_boot | op_write_erase_install | op_no_write_erase";
          }
      }

      output {
        leaf status {
            type int32;
            description "The status of the operation execution request.";
        }
        leaf status-detail {
            type string;
            description "The detailed status of the operation execution request.";
      }
    }
  }

  rpc factory-default-profile {
    description
      "This RPC is used to modify the factory default configuration profile.
       The user can specify a supported default configuration profile name as input
       and the RPC takes action to clear the existing switch configuration and creating a
       default configuration as per the input profile name. This operation can result
       in the restart of the REST server, thus the return status may not be available. When
       an error happens, the output parameter status returns a non-zero value and the
       the output parameter status-detail provides additional information about the
       error.";
    input {
      leaf profile-name {
        type string;
        description
          "Name of factory default configuration profile name.";
      }
    }
    output {
      leaf status {
        type int32;
        description
          "The status code of the operation execution request. A non-zero value
           indicates a failure.";
      }
      leaf status-detail {
        type string;
       description
          "The detailed status of the operation execution request.";
      }
    }
  }

  rpc default-port-config {
    description "This RPC is used to restore a selected port configuration to its
      factory default configuration state. When an error happens, the output parameter
      status returns a non-zero value and the the output parameter status-detail provides
      additional information about the error.";
    input {
      leaf ifname {
        type leafref {
          path "/prt:sonic-port/prt:PORT/prt:PORT_LIST/prt:ifname";
        }
      }
    }

    output {
      leaf status {
        type int32;
        description
          "The status code of the operation execution request. A non-zero value
          indicates a failure.";
      }
      leaf status-detail {
        type string;
        description
          "The detailed status of the operation execution request.";
      }
    }
  }
}
