module openconfig-qos-buffer {

  yang-version "1";

  // namespace
  namespace "http://openconfig.net/yang/qos/buffer/extension";

  prefix "oc-qos-buf";

  import openconfig-extensions { prefix oc-ext; }
  import openconfig-qos { prefix oc-qos; }
  import openconfig-interfaces { prefix oc-if; }

  organization "SONiC";

  contact
    "SONiC";

  description
    "This module defines YANG model for network quality-of-service buffer management.";

  oc-ext:openconfig-version "0.2.0";

  revision "2024-04-30" {
    description
      "Add cable length config";
    reference "0.2.0";
  }

  revision "2021-06-07" {
    description
      "Initial version";
    reference "0.1.0";
  }

  // typedef statements
  typedef qos-buffer-type {
    type enumeration {
      enum INGRESS {
        description
          "QoS buffer handling at the ingress in a switch";
      }
      enum EGRESS {
        description
          "QoS buffer handling at the egress in a switch";
      }
    }
    description
      "QoS buffer type selection";
  }

  typedef qos-buffer-mode {
    type enumeration {
      enum STATIC {
        description
          "QoS buffer static mode";
      }
      enum DYNAMIC {
        description
          "QoS buffer dynamic mode";
      }
    }
    description
      "QoS buffer mode selection";
  }

  grouping qos-buffer-pool-config {
    description
      "Individual Buffer pool definition";
    leaf name {
      type string;
      description
        "Buffer pool name";
    }

    leaf type {
      type qos-buffer-type;
      mandatory true;
      description
        "Indicate QoS buffer type ingress/egress";
    }

    leaf mode {
      type qos-buffer-mode;
      mandatory true;
      description
        "Indicate QoS buffer mode static/dynamic";
    }

    leaf size {
        type uint64;
        mandatory true;
        must "current() > current()/../xoff" {
            error-app-tag size-less-than-xoff;
            error-message "Pool Size must be greater than xoff";
        }
        description 
            "Buffer pool size";
    }

    leaf xoff {
        when "../type = 'INGRESS'";
        type uint64;
        must "current() < current()/../size" {
            error-app-tag size-less-than-xoff;
            error-message "Pool Size must be greater than xoff";
        }
        description
            "Shared headroom configuration";
    }
  }

  grouping qos-buffer-pool-top {
    description
      "Top-level grouping for buffer pool";

    container buffer-pools {
      description
        "Top-level container for buffer pool configuration";

      list buffer-pool {
        key "name";

        description
          "Uniquely identifies a pool name";

        leaf name {
          type leafref {
            path "../config/name";
          }
          description
            "Key for the buffer pool";
        }
        container config {
          description
            "Configuration Data";

          uses qos-buffer-pool-config;
        }
        container state {
          config false;

          description
            "Operational state data";

          uses qos-buffer-pool-config;
        }
      }
    }
  }

  grouping qos-buffer-profile-config {
    description
      "Individual Buffer profile definition";
    leaf name {
      type string;
      description
        "Buffer profile name";
    }

    leaf pool {
      type leafref {
        path "../../../../buffer-pools/buffer-pool/name";
      }
      mandatory true;
      description
        "Reference to buffer pool";
    }

    leaf type {
      type qos-buffer-type;
      mandatory true;
      description
        "Indicate QoS buffer type ingress/egress";
    }

    leaf size {
      type uint64;
      mandatory true;
      description 
        "Reserved buffer size in bytes";
    }

    leaf static-threshold {
      type uint64;
      must "not(current()/../dynamic-threshold)" {
        error-message "Configuring Static and dynamic threshold in the same profile is not allowed.";
      }
      description
        "Static threshold for the shared usage in bytes";
    }

    leaf dynamic-threshold {
      type int8 {
        range "-6..3";
      }
      must "not(current()/../static-threshold)" {
        error-message "Configuring Static and dynamic threshold in the same profile is not allowed.";
      }
      description
        "Dynamic threshold value";
    }

    leaf pause-threshold {
        when "../type = 'INGRESS'";
        type uint64;
        description
            "Indicate the threshold value to stop the traffic from peer";
    }

    leaf resume-threshold {
        when "../type = 'INGRESS'";
        type uint64;
        description
            "Indicate the threshold value to resume the traffic from peer.";
    }

    leaf resume-offset-threshold {
      when "../type = 'INGRESS'";
      type uint64;
      description
        "Indicate the resume threshold offset.";
    }
  }

  grouping qos-buffer-profile-top {
    description
      "Top-level grouping for buffer profile";

    container buffer-profiles {
      description
        "Top-level container for buffer profile configuration";

      list buffer-profile {
        key "name";

        description
          "Uniquely identifies a profile name";

        leaf name {
          type leafref {
            path "../config/name";
          }
          description
            "Key for the buffer profile";
        }
        container config {
          description
            "Configuration Data";

          uses qos-buffer-profile-config;
        }
        container state {
          config false;

          description
            "Operational state data";

          uses qos-buffer-profile-config;
        }
      }
    }
  }

  grouping qos-buffer-priority-group-config {
    description
      "Individual Buffer priority group definition";
    leaf ifname {
      type oc-if:base-interface-ref;

      description
        "Physical interface name";
    }

    leaf priority-group {
      type string {
        pattern "[0-7]?" {
          error-message "Invalid Buffer Priority-group number";
          error-app-tag pg-num-invalid;
        }
        oc-ext:posix-pattern '^[0-7]?$';
      }
      description
        "Priority group number, single PG number e.g 0";
    }

    leaf profile {
      type leafref {
        path "../../../../buffer-profiles/buffer-profile/name";
      }
      mandatory true;
      description
        "Reference to buffer profile";
    }
  }

  grouping qos-buffer-priority-group-top {
    description
      "Top-level grouping for buffer priority group";

    container buffer-priority-groups {
      description
        "Top-level container for buffer priority group configuration";

      list buffer-priority-group {
        key "ifname priority-group";

        description
          "Uniquely identifies a profile name";

        leaf ifname {
          type leafref {
            path "../config/ifname";
          }
          description
            "Key for the buffer profile";
        }

        leaf priority-group {
          type leafref {
            path "../config/priority-group";
          }
          description
            "Priority group number, single PG number or range e.g 0 or 3-4";
        }

        container config {
          description
            "Configuration Data";

          uses qos-buffer-priority-group-config;
        }
        container state {
          config false;

          description
            "Operational state data";

          uses qos-buffer-priority-group-config;
        }
      }
    }
  }

  grouping qos-buffer-queue-config {
    description
      "Individual Buffer queue definition";
    leaf ifname {
      type oc-if:base-interface-ref;
      description
        "Physical interface name";
    }

    leaf queue {
      type string {
        pattern "[0-7]?" {
          error-message "Invalid Queue index";
          error-app-tag qindex-invalid;
        }
        oc-ext:posix-pattern '^[0-7]$';
      }
      description
        "Queue number, single queue number e.g 0";
    }

    leaf profile {
      type leafref {
        path "../../../../buffer-profiles/buffer-profile/name";
      }
      mandatory true;
      description
        "Reference to buffer profile";
    }
  }

  grouping qos-buffer-queue-top {
    description
      "Top-level grouping for buffer queue";

    container buffer-queues {
      description
        "Top-level container for buffer queue configuration";

      list buffer-queue {
        key "ifname queue";

        description
          "Uniquely identifies a queue name";

        leaf ifname {
          type leafref {
            path "../config/ifname";
          }
          description
            "Interface name";
        }

        leaf queue {
          type leafref {
            path "../config/queue";
          }
          description
            "Queue number, single queue number or range e.g 0 or 3-4";
        }

        container config {
          description
            "Configuration Data";

          uses qos-buffer-queue-config;
        }
        container state {
          config false;

          description
            "Operational state data";

          uses qos-buffer-queue-config;
        }
      }
    }
  }

  grouping qos-buffer-top {  
    description
      "Top level QoS buffer data containers";

    container buffer {
      description
        "Enclosing container for QoS buffer related configuration and
        operational state data";

      uses qos-buffer-pool-top;
      uses qos-buffer-profile-top;
      uses qos-buffer-priority-group-top;
      uses qos-buffer-queue-top;
    }
  }

  grouping port-buffer-settings {
      description
          "QoS port buffer data settings";

      leaf default-lossless-buffer-profile {
          type boolean;
          default true;

          description
              "Default lossless buffer profile configuration on port";
      }
  }

  grouping qos-interface-buffer {
      description
          "QoS port buffer data containers";

      container buffer {
          description
              "QoS buffer details";

          container config {
              description
                  "Configuration buffer configuration for QoS";

              uses port-buffer-settings;
          }
          container state {
              config false;
              description
                  "Configuration buffer configuration for QoS";

              uses port-buffer-settings;
          }
      }
  }

  augment /oc-qos:qos/oc-qos:interfaces/oc-qos:interface {
      description
          "Configuration and operational pararmeters for port Qos Buffer";

      uses qos-interface-buffer;
  }

  augment /oc-qos:qos {
    description
      "Configuration and operational pararmeters for Qos-Buffer";

    uses qos-buffer-top;
  }

    grouping cable-length-config {
        description "cable length config";

        leaf length {
            type string {
                pattern '[0-9]+m' {
                    error-message "Invalid cable length.";
                    error-app-tag cable-length-invalid-length;
                }
                oc-ext:posix-pattern  '[0-9]+m';
            }
            description "cable length";
        }
    }

    grouping cable-length-config-top {
      description "cable length config";
      container cable-length {
        description "cable length config";

        container config {
            description "cable length config";
	        uses cable-length-config;
        }

        container state {
            config false;
            description "cable length config";
            uses cable-length-config;
        }
      }
    }	
       
    augment /oc-qos:qos/oc-qos:interfaces/oc-qos:interface {
      description "cable length configuration";
      uses cable-length-config-top;
    }

}
