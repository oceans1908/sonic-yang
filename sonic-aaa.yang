module sonic-aaa {
    namespace "http://github.com/Azure/sonic-aaa";
    prefix saaa;
    yang-version 1.1;

    import sonic-extension {
        prefix sonic-ext;
    }

    organization
        "SONiC";

    contact
        "SONiC";

    description
        "SONiC AAA";

    revision 2019-11-05 {
        description
            "Initial revision.";
    }

    container sonic-aaa {
        /*
        container USER_DB {
            list USER_TABLE {
                key "user tenant";

                leaf user {
                    type string {
                        pattern '[a-z_][a-z0-9_-]*[$]';
                        length 1..31;
                    }
                }

                leaf tenant {
                    type string;
                }

                leaf-list role {
                    type string;
                }
            }

            list PRIVILEGE_TABLE {
                key "role feature";

                leaf role {
                    type string;
                }

                leaf feature {
                    type string;
                }

                leaf permissions {
                    type string;
                }
            }
        }
        */

        container USER_TABLE {
            sonic-ext:db-name "STATE_DB";
            sonic-ext:key-delim "|";
            list USER_TABLE_LIST {
                key "user";

                leaf user {
                    type string {
                        pattern '[a-z_][a-z0-9_-]*[$]';
                        length 1..31;
                    }
                    description "Assigned username for a user.";
                }

                leaf-list roles {
                    type string;
                    description "Role(s) assigned to a user. Permissions granted
                        to the user will be based on the roles assigned.";
                }

                leaf usertype {
                    type enumeration {
                        enum local;
                        enum remote;
                    }
                    description "Flag to identify the user type.";
                }

                leaf ssh-key {
                    type string;
                    description "SSH public key for the user.";
                }
            }
        } // End of container USER_TABLE
    }
}
