submodule openconfig-aft-ipv4 {
  belongs-to "openconfig-aft" {
    prefix "oc-aft";
  }

  import openconfig-extensions { prefix "oc-ext"; }
  import openconfig-inet-types { prefix "oc-inet"; }

  // Include common cross-AFT groupings from the common submodule.
  include openconfig-aft-common;

  organization
    "OpenConfig working group";

  contact
    "OpenConfig working group
    www.openconfig.net";

  description
    "Submodule containing definitions of groupings for the abstract
    forwarding tables for IPv4.";

  oc-ext:openconfig-version "0.7.0";

  revision "2021-06-11" {
    description
      "Added AFT IPV4 Multicast.";
    reference "0.7.0";
  }

  revision "2020-11-06" {
    description
      "Make AFT model read-only.";
    reference "0.6.0";
  }

  revision "2020-09-09" {
    description
      "Remove leafs that are not used as keys from config containers as
      AFT model is ready-only.
      * next-hop/interface-ref/config.
      * all leafs under policy-forwarding-entry/config except index.";
    reference "0.5.0";
  }

  revision "2019-11-07" {
    description
      "Move lsp-name leaf out of aft-common-entry-nexthop-state group.";
    reference "0.4.1";
  }

  revision "2019-08-02" {
    description
      "Add installing protocol for IPv[46] unicast entries.
      Add the ability to describe conditional next-hop groups
      outside of the policy forwarding module to allow for efficient
      handling of CBTS, where many prefixes may share the same next-hop
      criteria.";
    reference "0.4.0";
  }

  revision "2019-08-01" {
    description
      "Add lsp-name leaf to AFT next-hop.";
    reference "0.3.3";
  }

  revision "2018-11-21" {
    description
      "Add OpenConfig module metadata extensions.";
    reference "0.3.2";
  }

  revision 2017-08-24 {
    description
      "Formatting fixes";
    reference "0.3.1";
  }

  revision 2017-05-10 {
    description
      "Refactor to provide concretised per-AF schemas per AFT.";
    reference "0.3.0";
  }

  grouping aft-ipv4-unicast-structural {
    description
      "Structural grouping defining the schema for the IPv4 unicast
      abstract forwarding table.";

    list ipv4-entry {
      key "prefix";

      description
        "List of the IPv4 unicast entries within the abstract
        forwarding table. This list is keyed by the destination IPv4
        prefix.";

      leaf prefix {
        type leafref {
          path "../state/prefix";
        }
        description
          "Reference to the IPv4 unicast destination prefix which
          must be matched to utilise the AFT entry.";
      }

      container state {
        config false;
        description
          "Operational state parameters for the IPv4 unicast AFT
          entry.";
        uses aft-ipv4-unicast-entry-state;
      }
    }
  }

  grouping aft-ipv4-unicast-entry-state {
    description
      "Operational state parameters for the IPv4 unicast entry.";
    leaf prefix {
        type oc-inet:ipv4-prefix;
        description
          "The IPv4 destination prefix that should be matched to
          utilise the AFT entry.";
    }
    uses aft-common-entry-state;
    uses aft-common-ip-state;
  }

  grouping aft-ipv4-multicast-structural {
    description
      "Structural grouping defining the schema for the IPv4 multicast abstract forwarding table.";

    container ipv4-entries {
      config false;
      description
        "Details about all IPv4 multicast entries present in forwarding table.";

      list ipv4-entry {
        key "group-address";

        description
          "List of the IPv4 multicast entries within the abstract forwarding table.
          This list is keyed by the destination IPv4 multicast group & source address.";

        leaf group-address {
          type leafref {
              path "../state/group-address";
          }
          description
              "Reference to the group-address key";
        }

        container state {
          description "Operational state information.";

          leaf group-address {
            type oc-inet:ipv4-address;
            description
              "IPv4 Multicast group-address";
          }
        }

        container src-entries {
          description
            "Details about all multicast-source information of this particular multicast group-address entry.";

          list src-entry {
            key "source-address";

            description
              "List of different source-address entries within this particular multicast group-address entry.";

            leaf source-address {
              type leafref {
                path "../state/source-address";
              }
              description
                "Reference to the source-address key";
            }

            container state {
              description
                "Operational state parameters for the IPv4 multicast AFT entry.";

              leaf source-address {
                type oc-inet:ipv4-address;
                description
                  "IPv4 Unicast source-address of the device, which originates this particular multicast group traffic.
                  This address can be 0.0.0.0 in case of *,G multicast group entry.";
              }

              uses aft-common-ip-mcast-entry-state;
            }

            uses aft-common-ip-mcast-entry-oil-info-entries-top;
          }
        }
      }
    }
  }
}
