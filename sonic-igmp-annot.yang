module sonic-igmp-annot {

    yang-version "1";

    namespace "http://openconfig.net/yang/annotation/sonic-igmp-annot";
    prefix "sigmp-annot";

    import sonic-igmp { prefix sigmp; }
    import sonic-extensions { prefix sonic-ext; }

    deviation /sigmp:get-igmp-join {
        deviate add {
            sonic-ext:rpc-callback "rpc_show_igmp_join";
        }
    }

    deviation /sigmp:clear-igmp {
        deviate add {
            sonic-ext:rpc-callback "rpc_clear_igmp";
        }
    }
}
