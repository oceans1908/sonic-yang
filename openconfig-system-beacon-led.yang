module openconfig-system-beacon-led {

    yang-version "1";

    namespace "http://openconfig.net/yang/system/beacon-led/extension";

    prefix "oc-sys-beacon";

    import openconfig-system { prefix oc-sys; }
    import openconfig-extensions { prefix oc-ext; }


    organization
        "Broadcom Inc.";
    contact
        "SONiC";
    description
        "SONIC Beacon LED";

    revision 2021-07-29 {
        description
            "Initial revision.";
        reference
            "0.1.0";
    }

    oc-ext:openconfig-version "0.1.0";

    typedef beacon-led-port-locator-mode {
        type enumeration {
            enum OFF {
                description
                    "OFF";
            }
            enum ON {
                description
                    "ON";
            }
        }
        description
            "Beacon-LED: Port-Locator Mode";
    }

    grouping system-beacon-led-port-locator-config
    {
        description
            "Port-Locator configuration group";

        leaf mode {
            type beacon-led-port-locator-mode;
            description
                "Port-Locator Mode(ON/OFF)";
        }
        leaf expire-time {
            type string;
            description
                "Expected expire time for disabling Port-Locator Mode";
        }
    }

    grouping system-beacon-led-top
    {
        description
            "Top level grouping for Beacon-LED";
        container port-locators {
            description
               "Container for Port-locator List";

        list port-locator
        {
            key "ifname";
            description
                "Top level container for Port-Locator LED";

            leaf ifname {
                type leafref {
                    path "../config/ifname";
                }
                description
                    "Interface ID";
            }
            container config
            {
                description
                    "Configuration parameters for Port-Locator LED";

                leaf ifname {
                    type string;
                    description
                        "Interface ID";
                }
                uses system-beacon-led-port-locator-config;
            }
            container state
            {
                config false;
                description
                    "State information of Port-Locator LED";

                leaf ifname {
                    type leafref {
                        path "../../config/ifname";
                    }
                    description
                        "Interface ID";
                }
                uses system-beacon-led-port-locator-config;
            }
        }
      }
    }

    augment /oc-sys:system {
        description
            "Beacon-LED";
        uses system-beacon-led-top;
    }
}
