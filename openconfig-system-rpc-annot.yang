module openconfig-system-rpc-annot {

    yang-version "1";

    namespace "http://openconfig.net/yang/system-rpc-annot";
    prefix "oc-sys-rpc-annot";

    import sonic-extensions { prefix sonic-ext; }

    import openconfig-system-rpc {prefix oc-sys-rpc; }


    deviation /oc-sys-rpc:show-system-status {
        deviate add {
            sonic-ext:rpc-callback "rpc_sys_status_cb";
        }
    }

    deviation /oc-sys-rpc:show-system-status-brief {
        deviate add {
            sonic-ext:rpc-callback "rpc_sys_status_brief_cb";
        }
    }

    deviation /oc-sys-rpc:show-system-status-detail {
        deviate add {
            sonic-ext:rpc-callback "rpc_sys_status_detail_cb";
        }
    }
    deviation /oc-sys-rpc:show-system-status-core {
        deviate add {
            sonic-ext:rpc-callback "rpc_sys_status_core_cb";
        }
    }

    deviation /oc-sys-rpc:clear-nhg-statistics {
      deviate add {
        sonic-ext:rpc-callback "rpc_oc_clear_nhg_counters";
        sonic-ext:user-role-priv "rpc:netadmin";
      }
    }

    deviation /oc-sys-rpc:clear-user-sessions {
      deviate add {
        sonic-ext:rpc-callback "rpc_oc_clear_user_sessions";
      }
    }

    deviation /oc-sys-rpc:set-system-datetime {
        deviate add {
            sonic-ext:rpc-callback "rpc_set_sys_datetime_cb";
            sonic-ext:user-role-priv "rpc:secadmin,netadmin";
        }
    }

    deviation /oc-sys-rpc:show-reboot-cause-history {
        deviate add {
            sonic-ext:rpc-callback "rpc_sys_reboot_cause_history_cb";
        }
    }
}
