module openconfig-system-rpc {

  yang-version "1";

  // namespace
  namespace "http://openconfig.net/yang/system-rpc/extension";

  prefix "oc-sys-rpc"; 

  import openconfig-extensions { prefix oc-ext; }
  import openconfig-yang-types { prefix oc-yang; }
  
  // meta
  organization
    "SONiC";

  contact
    "OCP SONiC Subproject Working Group
     https://github.com/Azure/SONiC";

  description
    "This module defines RPCs for system wide services";

  oc-ext:openconfig-version "0.1.0";

  revision "2022-09-28" {
    description
      "Initial revision";
    reference "0.1.0";
  }
 
  revision "2024-06-06" {
    description
      "Adding an RPC for clearing user sessions";
    reference "0.1.1";
  }

  revision "2025-03-21" {
    description
      "Adding an RPC for showing reboot-cause history";
    reference "0.1.2";
  }

  grouping status-state {
      description
          "Operation status";

      leaf status {
        type int32;
        description
          "The status of the operation execution request.";
      }
      leaf-list status-detail {
            type string;
            description "The detailed status of the operation execution request.";
      }

  }

  //rpcs
  rpc show-system-status {
     description "Display the system ready status";

     output {
        uses oc-sys-rpc:status-state;
     }
  }

  rpc show-system-status-brief {
     description "Display the detailed system ready status";

     output {
        uses oc-sys-rpc:status-state;
     }
  }

  rpc show-system-status-detail {
     description "Display the detailed system ready status";

     output {
        uses oc-sys-rpc:status-state;
     }
  }

  rpc show-system-status-core {
     description "Display the core system ready status";

     output {
        uses oc-sys-rpc:status-state;
     }
  }
 
  // adaptive-routing-and-switching
  rpc clear-nhg-statistics {
    description "RPC for clearing NHG statistics. Input can be :
      1. Single NHG ID
      2. All NHG IDs";

    input {
     leaf nhg-id {
       type union {
         type uint32;
         type string;
       }
       description
         "all or one nhgid as input";
     }
    }

    output {
      leaf status {
        type int32;
        description
          "The status of the operation execution request.";
      }
      leaf status-detail {
        type string;
        description
          "The detailed status of the operation execution request.";
      }
    }
  }

  // It closes all active sessions of the given user.
  rpc clear-user-sessions {
    description
      "RPC for clearing all active sessions of a user.";

    input {
      leaf username {
        type string;
        description
          "User whose sessions require closing.";
      }
    }

    output {
      leaf status {
        type uint32;
        description
          "The status of the clear operation. 0 for SUCCESS and 1 for FAILURE.";
      }
      leaf status-detail {
        type string;
        description
          "The detailed status of the operation execution status.";
      }
    }
  }

  rpc set-system-datetime {
     description "Set the system date and time to the specified value";

     input {
        leaf datetime {
           type oc-yang:date-and-time;
           description
              "System date and time";
        }
     }

     output {
        leaf status {
           type int32;
           description
              "The status of the operation execution request.";
        }
        leaf status-detail {
           type string;
           description
              "The detailed status of the operation execution request.";
        }
     }
  }
  
  rpc show-reboot-cause-history {
    description "Display reboot cause history of a device";

    output {
      list reboot-cause-history {
        key name;
        leaf name {
          type string;
        }
        leaf cause {
          type string;
        }
        leaf time {
          type string;
        }
        leaf user {
          type string;
        }
        leaf comment {
          type string;
        }
      }
    }
  }
}
