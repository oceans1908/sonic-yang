module sonic-loadshare-mode {
    namespace "http://github.com/Azure/sonic-loadshare-mode";
    prefix slbmode;
    yang-version 1.1;

    import sonic-extension {
        prefix sonic-ext;
    }

    import sonic-common {
        prefix cmn;
    }

    import ietf-inet-types {
        prefix inet;
    }

    import sonic-mgmt-vrf {
        prefix mvrf;
    }

    import sonic-vrf {
        prefix svrf;
    }

    organization
        "SONiC";

    contact
        "SONiC";

    description
        "SONIC Load Balance Mode";

    revision 2024-08-15 {
        description
	        "Added udf hash support";
    }

    revision 2021-01-08 {
        description
	        "Added symmetric hash support";
    }

    revision 2020-10-08 {
        description
	        "Initial revision.";
    }

    container sonic-loadshare-mode {
        container ECMP_LOADSHARE_TABLE_SEED {
            list ECMP_LOADSHARE_TABLE_SEED_LIST {
                key "hash";

                leaf hash {
                    type string;
                    description
                        "switch_table db key.";
                    sonic-ext:custom-validation KeyUpdateValidate;
                }

                leaf ecmp_hash_seed {
                    type uint32;
                    description
                        "ecmp hash seed value.";
                }
            }
        }
        container ECMP_LOADSHARE_TABLE_RH {
            list ECMP_LOADSHARE_TABLE_RH_LIST {

                key "vrf prefix";

                leaf vrf {
                    type union {
                        type string {
                            pattern "default|mgmt";
                        }
                        type leafref {
                            path "/svrf:sonic-vrf/svrf:VRF/svrf:VRF_LIST/svrf:vrf_name";
                        }
                    }
                    must "(/cmn:operation/cmn:operation = 'DELETE') or " +
                         "(current() != 'mgmt')" {
                        error-message "RH Config on Management VRF not allowed";
                        error-app-tag mgmt-vrf-not-allowed;
                    }
                    description
                      "The VRF to which this RH entry belongs.";
                }
                leaf prefix {
                    type inet:ip-prefix;
                    description
                        "The prefix member in CIDR notation -- while the
                        prefix may be either IPv4 or IPv6, most
                        implementations require all members of the prefix set
                        to be the same address family.  Mixing address types in
                        the same prefix set is likely to cause an error.";
                    must "(/cmn:operation/cmn:operation != 'CREATE') or (count(current()/../../ECMP_LOADSHARE_TABLE_RH_LIST) < 17)" {
                        error-message "Maximum resilient prefix count(16) reached";
                        error-app-tag max-rh-pfx-reached;
                    }
                }
                leaf size {
                    type uint16;
                    sonic-ext:custom-validation RhValidation;
                    description "size value";
                }
                leaf seed {
                    type uint32;
                    sonic-ext:custom-validation RhValidation;
                    description "seed value";
                }
            }
        }
        container ECMP_LOADSHARE_TABLE_OFFSET {
            list ECMP_LOADSHARE_TABLE_OFFSET_LIST {
                key "hash";

                leaf hash {
                    type string;
                    description
                        "switch_table db key.";
                }

                leaf ecmp-hash-offset {
                    type uint16;
                    description
                        "ecmp hash offset value.";
                }

                leaf ecmp-hash-flow-based {
                    sonic-ext:custom-validation IsMacroFlowSupported;
                    type boolean;
                    description
                        "ecmp hash auto offset enable flag.";
                }
            }
        }
        container ECMP_LOADSHARE_TABLE_INGRESS_PORT {
            list ECMP_LOADSHARE_TABLE_INGRESS_PORT_LIST {
                key "hash";

                leaf hash {
                    type string;
                    description
                        "switch_table db key.";
                }

                leaf ingress-port {
                    type boolean;
                    description
                        "ecmp hash ingress-port enable flag.";
                    must "current() = 'false' or (not(/sonic-loadshare-mode/ECMP_LOADSHARE_TABLE_IPV4/ECMP_LOADSHARE_TABLE_IPV4_LIST[ipv4='ipv4']/ipv4_symmetric)) or
                         (/sonic-loadshare-mode/ECMP_LOADSHARE_TABLE_IPV4/ECMP_LOADSHARE_TABLE_IPV4_LIST[ipv4='ipv4']/ipv4_symmetric = 'false')" {
                        error-message "Both ingress-port and ipv4 symmetric cannot be configured together.";
                    }
                    must "current() = 'false' or (not(/sonic-loadshare-mode/ECMP_LOADSHARE_TABLE_IPV6/ECMP_LOADSHARE_TABLE_IPV6_LIST[ipv6='ipv6']/ipv6_symmetric)) or
                         (/sonic-loadshare-mode/ECMP_LOADSHARE_TABLE_IPV6/ECMP_LOADSHARE_TABLE_IPV6_LIST[ipv6='ipv6']/ipv6_symmetric = 'false')" {
                        error-message "Both ingress-port and ipv6 symmetric cannot be configured together.";
                    }
                    must "current() = 'false' or (count(/sonic-loadshare-mode/ECMP_LOADSHARE_TABLE_UDF/ECMP_LOADSHARE_TABLE_UDF_LIST) = 0)" {
                        error-message "Both ingress-port and UDF cannot be configured together.";
                    }
                }
            }
        }
        container ECMP_LOADSHARE_TABLE_ROCE {
            list ECMP_LOADSHARE_TABLE_ROCE_LIST {
                key "hash";

                leaf hash {
                    sonic-ext:custom-validation IsRoceHashSupported;
                    sonic-ext:custom-validation KeyUpdateValidate;
                    type string;
                    description
                        "switch_table db key.";
                    must "current() = 'false' or (not(/sonic-loadshare-mode/ECMP_LOADSHARE_TABLE_IPV4/ECMP_LOADSHARE_TABLE_IPV4_LIST[ipv4='ipv4']/ipv4_symmetric)) or
                         (/sonic-loadshare-mode/ECMP_LOADSHARE_TABLE_IPV4/ECMP_LOADSHARE_TABLE_IPV4_LIST[ipv4='ipv4']/ipv4_symmetric = 'false')" {
                        error-message "Both qpn and ipv4 symmetric cannot be configured together.";
                    }
                    must "current() = 'false' or (not(/sonic-loadshare-mode/ECMP_LOADSHARE_TABLE_IPV6/ECMP_LOADSHARE_TABLE_IPV6_LIST[ipv6='ipv6']/ipv6_symmetric)) or
                         (/sonic-loadshare-mode/ECMP_LOADSHARE_TABLE_IPV6/ECMP_LOADSHARE_TABLE_IPV6_LIST[ipv6='ipv6']/ipv6_symmetric = 'false')" {
                        error-message "Both qpn and ipv6 symmetric cannot be configured together.";
                    }
                }

                leaf qpn {
                    type boolean;
                    description "ecmp hash mode roce qpn enable flag.";
                }
            }
        }
        container ECMP_LOADSHARE_TABLE_UDF {
            list ECMP_LOADSHARE_TABLE_UDF_LIST {
                key "udf-name";

                leaf udf-name {
                    sonic-ext:custom-validation IsRoceHashSupported;
                    type string;
                    description "User-defined field name";

                    must "current() = 'false' or (not(/sonic-loadshare-mode/ECMP_LOADSHARE_TABLE_IPV4/ECMP_LOADSHARE_TABLE_IPV4_LIST[ipv4='ipv4']/ipv4_symmetric)) or
                         (/sonic-loadshare-mode/ECMP_LOADSHARE_TABLE_IPV4/ECMP_LOADSHARE_TABLE_IPV4_LIST[ipv4='ipv4']/ipv4_symmetric = 'false')" {
                        error-message "UDF and ipv4 symmetric hashing cannot be configured together";
                    }
                    must "current() = 'false' or (not(/sonic-loadshare-mode/ECMP_LOADSHARE_TABLE_IPV6/ECMP_LOADSHARE_TABLE_IPV6_LIST[ipv6='ipv6']/ipv6_symmetric)) or
                         (/sonic-loadshare-mode/ECMP_LOADSHARE_TABLE_IPV6/ECMP_LOADSHARE_TABLE_IPV6_LIST[ipv6='ipv6']/ipv6_symmetric = 'false')" {
                        error-message "UDF and ipv6 symmetric hashing cannot be configured together";
                    }
                    must "current() = 'false' or (not(/sonic-loadshare-mode/ECMP_LOADSHARE_TABLE_INGRESS_PORT/ECMP_LOADSHARE_TABLE_INGRESS_PORT_LIST[hash='hash']))" {
                        error-message "UDF and ingress-port cannot be configured together";
                    }
                }

                leaf udf-offset {
                    type uint16;
                    description "User-defined field offset post IP header";
                }

                leaf udf-size {
                    type uint16;
                    description "User-defined field size";
                }

                leaf l3-proto {
                    type uint8;
                    description "L3 protocol to match traffic flows";
                }

                leaf l4-dst-port {
                    type uint16;
                    description "L4 dst port to match traffic flows";
                }
            }
        }
        container ECMP_LOADSHARE_TABLE_IPV4 {
            list ECMP_LOADSHARE_TABLE_IPV4_LIST {
                key "ipv4";

                leaf ipv4 {
                    type string;
                    description
                        "switch_table ipv4 db key.";
                }
                leaf ipv4_l4_src_port {
                    type boolean;
                    default true;
                    description
                        "Flag to enable or disable ipv4_l4_src_port attribute";
                }
                leaf ipv4_l4_dst_port {
                    type boolean;
                    default true;
                    description
                        "Flag to enable or disable ipv4_l4_dst_port attribute";
                }
                leaf ipv4_src_ip {
                    type boolean;
                    default true;
                    description
                        "Flag to enable or disable ipv4_src_ip attribute";
                }
                leaf ipv4_dst_ip {
                    type boolean;
                    default true;
                    description
                        "Flag to enable or disable ipv4_dst_ip attribute";
                }
                leaf ipv4_protocol {
                    type boolean;
                    default true;
                    description
                        "Flag to enable or disable ipv4_protocol attribute";
                }
                leaf ipv4_symmetric {
                    type boolean;
                    default false;
                    sonic-ext:custom-validation ValidateSymmHashCfg;
                    description
                        "Flag to enable or disable ipv4_symmetric attribute";
                    must "current() = 'false' or (not(/sonic-loadshare-mode/ECMP_LOADSHARE_TABLE_INGRESS_PORT/ECMP_LOADSHARE_TABLE_INGRESS_PORT_LIST[hash='hash']))" {
                        error-message "Ingress-port and ipv4 symmetric hash cannot be configured together";
                    }
                }
            }
        }
        container ECMP_LOADSHARE_TABLE_IPV6 {
            list ECMP_LOADSHARE_TABLE_IPV6_LIST {
                key "ipv6";

                leaf ipv6 {
                    type string;
                    description
                        "switch_table ipv6 db key.";
                }
                leaf ipv6_l4_src_port {
                    type boolean;
                    default true;
                    description
                        "Flag to enable or disable ipv6_l4_src_port attribute";
                }
                leaf ipv6_l4_dst_port {
                    type boolean;
                    default true;
                    description
                        "Flag to enable or disable ipv6_l4_dst_port attribute";
                }
                leaf ipv6_src_ip {
                    type boolean;
                    default true;
                    description
                        "Flag to enable or disable ipv6_src_ip attribute";
                }
                leaf ipv6_dst_ip {
                    type boolean;
                    default true;
                    description
                        "Flag to enable or disable ipv6_dst_ip attribute";
                }
                leaf ipv6_next_hdr {
                    type boolean;
                    default true;
                    description
                        "Flag to enable or disable ipv6_next_hdr attribute";
                }
                leaf ipv6_flow_label {
                    type boolean;
                    default false;
                    description
                        "Flag to enable or disable ipv6_flow_label attribute";
                }
                leaf ipv6_symmetric {
                    type boolean;
                    default false;
                    sonic-ext:custom-validation ValidateSymmHashCfg;
                    description
                        "Flag to enable or disable ipv6_symmetric attribute";
                    must "current() = 'false' or (not(/sonic-loadshare-mode/ECMP_LOADSHARE_TABLE_INGRESS_PORT/ECMP_LOADSHARE_TABLE_INGRESS_PORT_LIST[hash='hash']))" {
                        error-message "Ingress-port and ipv6 symmetric hash cannot be configured together";
                    }
                }
            }
        }
    }
}
