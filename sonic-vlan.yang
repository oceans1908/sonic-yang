module sonic-vlan {
    namespace "http://github.com/Azure/sonic-vlan";
    prefix svlan;
    yang-version 1.1;

    import ietf-inet-types {
        prefix inet;
    }

    import sonic-common {
        prefix scommon;
    }

    import sonic-extension {
        prefix sonic-ext;
    }

    import sonic-port {
        prefix prt;
    }

    import sonic-portchannel {
        prefix spc;
    }

    import sonic-vrf {
        prefix vrf;
    }

    organization
        "SONiC";

    contact
        "SONiC";

    description
        "SONIC VLAN";

    revision 2023-01-10 {
        description
            "Add custom validation for VLAN member.";
    }

    revision 2021-11-09 {
        description
            "Add description leaf in vlan table container.";
    }

    revision 2020-07-30 {
        description
            "Add Vlan description.";
    }

    revision 2019-05-15 {
        description
            "Initial revision.";
    }


    container sonic-vlan {

        container VLAN { 

            list VLAN_LIST { 
                key "name";
                must "./name = concat('Vlan', string(./vlanid))"
                {
                    error-message "Invalid Vlan";
                    error-app-tag vlan-invalid;
                }

                leaf name {
                    sonic-ext:custom-validation ValidateVlanConfig;
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                }

                leaf vlanid {
                    mandatory true;
                    type uint16 {
                        range "1..4095" {
                            error-message "Vlan ID out of range";
                            error-app-tag vlanid-invalid;
                        }
                    }
                }

                leaf-list members {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }
                leaf mtu  {
                    type uint32 {
                        range "1312..9216" {
                            error-message "Invalid MTU value";
                            error-app-tag mtu-invalid;
                        }
                    }
                }

                leaf admin_status {
                    type scommon:admin-status;
                }

                leaf-list dhcp_servers{
                     max-elements 16;
                     type inet:ip-address;
                }

                leaf-list dhcpv6_servers{
                     max-elements 16; 
                     type inet:ipv6-address;
                }

                leaf dhcp_relay_link_select {
                      type scommon:mode-enable;
                      must "((/scommon:operation/scommon:operation != 'CREATE') and (/scommon:operation/scommon:operation != 'UPDATE')) or " +
                             "(current()/../dhcp_relay_src_intf)"
                              {
                                    error-message "DHCP relay source interface not configured";
                                    error-app-tag dhcp-server-adress-config;
                              }
                }

                leaf dhcp_relay_src_intf {
                      type string;
                      must "((/scommon:operation/scommon:operation != 'CREATE') and (/scommon:operation/scommon:operation != 'UPDATE')) or " +
                             "(current()/../dhcp_servers)"
                              {
                                    error-message "DHCP relay address not configured";
                                    error-app-tag dhcp-server-adress-config;
                              }
                } 

                leaf dhcp_relay_max_hop_count {
                     type uint32;
                     must "((/scommon:operation/scommon:operation != 'CREATE') and (/scommon:operation/scommon:operation != 'UPDATE')) or " +
                            "(current()/../dhcp_servers)"
                             {
                                   error-message "DHCP relay address not configured";
                                   error-app-tag dhcp-server-adress-config;
                             }
                }
                leaf dhcp_server_vrf {
                     type union {
                         type string {
                             pattern "mgmt";
                         }
                         type leafref {
                             path "/vrf:sonic-vrf/vrf:VRF/vrf:VRF_LIST/vrf:vrf_name";
                         }
                     }
                     must "((/scommon:operation/scommon:operation != 'CREATE') and (/scommon:operation/scommon:operation != 'UPDATE')) or " +
                           "(current()/../dhcp_servers)"
                            {
                                  error-message "DHCP server not configured";
                                  error-app-tag dhcp-server-invalid-vrf-config;
                            }
                }

                leaf dhcp_relay_vrf_select {
                     type scommon:mode-enable;
                     must "((/scommon:operation/scommon:operation != 'CREATE') and (/scommon:operation/scommon:operation != 'UPDATE')) or " +
                            "(current()/../dhcp_servers)"
                             {
                                   error-message "DHCP relay address not configured";
                                   error-app-tag dhcp-server-adress-config;
                             }
                }

                leaf dhcp_relay_policy_action {
                     type scommon:relay-policy-action;
                     must "((/scommon:operation/scommon:operation != 'CREATE') and (/scommon:operation/scommon:operation != 'UPDATE')) or " +
                            "(current()/../dhcp_servers)"
                             {
                                   error-message "DHCP relay address not configured";
                                   error-app-tag dhcp-server-adress-config;
                             }
                }

                leaf dhcp_relay_circuit_id_format {
                     type string;
                     must "((/scommon:operation/scommon:operation != 'CREATE') and (/scommon:operation/scommon:operation != 'UPDATE')) or " +
                            "(current()/../dhcp_servers)"
                     {
                         error-message "DHCP server not configured";
                         error-app-tag dhcp-server-address-config;
                     }
                }

                leaf dhcp_relay_smart_mode {
                     type scommon:mode-enable;
                     description "Enable/Disable smart relay mode on the vlan interface.";
                     must "((/scommon:operation/scommon:operation != 'CREATE') and (/scommon:operation/scommon:operation != 'UPDATE')) or " +
                            "(current()/../dhcp_servers)"
                     {
                         error-message "DHCP server not configured";
                         error-app-tag dhcp-server-address-config;
                     }
                }

                leaf dhcpv6_relay_src_intf {
                     type string;
                     must "((/scommon:operation/scommon:operation != 'CREATE') and (/scommon:operation/scommon:operation != 'UPDATE')) or " +
                            "(current()/../dhcpv6_servers)"
                             {
                                   error-message "DHCP relay address not configured";
                                   error-app-tag dhcp-server-adress-config;
                             }
                }

                leaf dhcpv6_relay_max_hop_count {
                     type uint32;
                     must "((/scommon:operation/scommon:operation != 'CREATE') and (/scommon:operation/scommon:operation != 'UPDATE')) or " +
                            "(current()/../dhcpv6_servers)"
                             {
                                   error-message "DHCP relay address not configured";
                                   error-app-tag dhcp-server-adress-config;
                             }
                }

                leaf dhcpv6_server_vrf {
                     type union {
                         type string {
                             pattern "mgmt";
                         }
                         type leafref {
                             path "/vrf:sonic-vrf/vrf:VRF/vrf:VRF_LIST/vrf:vrf_name";
                         }
                     }
                     must "((/scommon:operation/scommon:operation != 'CREATE') and (/scommon:operation/scommon:operation != 'UPDATE')) or " +
                            "(current()/../dhcpv6_servers)"
                             {
                                   error-message "DHCP relay address not configured";
                                   error-app-tag dhcp-server-adress-config;
                             }
                }

               leaf dhcpv6_relay_vrf_select {
                    type scommon:mode-enable;
                    must "((/scommon:operation/scommon:operation != 'CREATE') and (/scommon:operation/scommon:operation != 'UPDATE')) or " +
                           "(current()/../dhcpv6_servers)"
                            {
                                  error-message "DHCP relay address not configured";
                                  error-app-tag dhcp-server-adress-config;
                            }
                }

                leaf description {
                    type string;
                }
                leaf autostate {
                    type scommon:mode-enable;
                    description
                        "When enabled the operstatus of the vlan will be controlled by its members. When disabled the operstatus is the same as the admin status";
                    default enable;
                }
                leaf dhcpv4_snooping_enable {
                      type scommon:mode-enable;
                }
                leaf dhcpv6_snooping_enable {
                      type scommon:mode-enable;
                }
	    }
        }

        container VLAN_MEMBER { 

            list VLAN_MEMBER_LIST { 
                key "name ifname";

                leaf name {
                    type leafref {
                        path "../../../VLAN/VLAN_LIST/name";
                    }
                }

                leaf ifname {
                    sonic-ext:custom-validation ValidateVlanMember;
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf tagging_mode {
                    type scommon:tagging_mode;
                    default tagged;
                }
            }
        }


        container VLAN_TABLE {
            config false;

            list VLAN_TABLE_LIST {
                key "name";
                must "./name = concat('Vlan', string(./vlanid))" {
                    error-app-tag vlan-invalid;
                }

                leaf name {
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                }

                leaf admin_status {
                    type scommon:admin-status;
                }  

                leaf mtu {
                    type uint32 {
                        range "1312..9216" {
                            error-message "Invalid MTU value";
                            error-app-tag mtu-invalid;
                        }
                    }
                }  

                leaf oper_status {
                    type scommon:oper-status;
                }
                leaf autostate {
                    type scommon:mode-enable;
                }

                leaf description {
                    type string;
                }
            }
        }

        container VLAN_MEMBER_TABLE {
            config false;

            list VLAN_MEMBER_TABLE_LIST {
                key "name ifname";

                leaf name {
                    type leafref {
                        path "../../../VLAN_TABLE/VLAN_TABLE_LIST/name";
                    }
                }

                leaf ifname {
                    type leafref {
                        path "/prt:sonic-port/prt:PORT/prt:PORT_LIST/prt:ifname";
                    }
                }

                leaf tagging_mode {
                    type scommon:tagging_mode;
                }  

                leaf dynamic {
                    type scommon:dynamic_member_flag;
                }
            }
        }
        container RESERVED_VLAN {
            list RESERVED_VLAN_LIST {
                key "vlan-name";
                max-elements 128;
                
                leaf vlan-name {
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                }
            }
        }

        container OPER_VLAN {
            config false;
            sonic-ext:db-name "STATE_DB"; 
            sonic-ext:key-delim "|"; 
            description "state db dynamic vlan table used by PAC";

            list OPER_VLAN_LIST {
                key "vlan-name";

                leaf vlan-name {
                    type string;

                }
                leaf vlanid {
                    type uint16;
                }
                leaf admin {
                    type scommon:admin-status;
                }
            }
        }

        container OPER_VLAN_MEMBER {
            config false;
            sonic-ext:db-name "STATE_DB"; 
            sonic-ext:key-delim "|"; 
            description "state db dynamic vlan membership table used by PAC";

            list OPER_VLAN_MEMBER_LIST {
                key "name ifname";

                leaf name {
                    type string;
                }

                leaf ifname {
                    type string;
                }
            }
        }
 
    }

}
