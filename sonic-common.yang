module sonic-common {
    namespace "http://github.com/Azure/sonic-common";
    prefix scommon;

    organization
        "SONiC";

    contact
        "SONiC";

    description
        "SONIC Common";

    revision 2024-09-18 {
        description
            "Added Extended fec types.";
    }

    revision 2021-07-05 {
        description
            "Added media fec-mode type.";
    }

    revision 2020-08-04 {
        description
            "Added fec-mode type.";
    }

    revision 2019-05-15 {
        description
            "Initial revision.";
    }

    typedef tagging_mode {
        type enumeration {
            enum untagged;
            enum tagged;
            enum priority_tagged;
        }
    }

    typedef dynamic_member_flag {
        type enumeration {
            enum yes;
            enum no;
        }
    }

    typedef admin-status {
        type enumeration {
            enum up;
            enum down;
        }
    }

    typedef oper-status {
        type enumeration {
            enum up;
            enum down;
        }
    }

   /* typedef down-reason {
        type enumeration {
            enum up;
            enum phy_link_down;
            enum err_disabled;
            enum admin_down;
        }
    }*/

    typedef mode-enable {
          type enumeration {
              enum enable;
              enum disable;
          }
      }

    typedef mode-on-off {
          type enumeration {
              enum off;
              enum on;
          }
      }

    typedef mode-on-off-auto {
          type enumeration {
              enum auto;
              enum off;
              enum on;
          }
      }

    typedef fec-mode {
          type enumeration {
              enum auto;
              enum rs;
              enum fc;
              enum none;
              enum rs528;
              enum rs544;
              enum rs544_2xn;
          }
      }

    typedef duplex-mode {
          type enumeration {
              enum full;
              enum half;
          }
      }


     typedef media-fec-mode-type{
          type enumeration {
              enum ieee;
              enum custom;
          }
     }

     typedef relay-policy-action {
          type enumeration {
              enum discard;
              enum append;
              enum replace;
            }
    }

    typedef percentage {
        type uint8 {
            range "0..100";
        }
        description
            "Integer indicating a percentage value";
    }

    typedef down-reason {
        type enumeration {
            enum OPER_UP;
            enum PHY_LINK_DOWN;
            enum ERR_DISABLED;
            enum NO_TRANSCEIVER;
            enum ADMIN_DOWN;
            enum ALL_LINKS_DOWN;
            enum LACP_FAIL;
            enum MIN_LINKS;
        }
    }

    container operation {
	    leaf operation {
		    type enumeration {
			    enum CREATE;
			    enum UPDATE;
			    enum DELETE;
		    }
	    }
    }

    typedef timeticks64 {
      type uint64;
      description
        "Time represented as ticks with 64-bit width.
         This value is expressed as nanoseconds since the Unix Epoch.";
    }

    typedef stack_stage {
        description "VLAN stacking/translation direction";
        type enumeration {
            enum INGRESS;
            enum EGRESS;
        }
    }
    
    typedef dad-mode {
        description "Duplicate Address Detection config mode";
        type enumeration {
            enum disable;
            enum enable;
            enum disable-ipv6-on-dad-failure;
        }
    }

    typedef proxy-mode {
        description "Proxy config modes";
          type enumeration {
              enum remote-only;
              enum all;
              enum disable;
          }
    }
}
