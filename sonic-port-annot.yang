module sonic-port-annot {

    yang-version "1.1";

    namespace "http://openconfig.net/yang/annotation/prt-annot";
    prefix "prt-annot";

    import sonic-extensions { prefix sonic-ext; }
    import sonic-port { prefix prt; }

    deviation /prt:sonic-port {
        deviate add {
            sonic-ext:user-role-priv "write:secadmin,netadmin";
        }
    }

    deviation /prt:sonic-port/prt:PORT_TABLE {
        deviate add {
            sonic-ext:db-name "APPL_DB";
        }
    }
    deviation /prt:sonic-port/prt:PORT/prt:PORT_LIST/prt:ifname {
        deviate add {
            sonic-ext:value-transformer "alias_value_xfmr";
        }
    }

    deviation /prt:sonic-port/prt:PORT_TABLE/prt:PORT_TABLE_LIST/prt:alias {
        deviate add {
            sonic-ext:value-transformer "alternate_name_value_xfmr";
        }
    }

    deviation /prt:sonic-port/prt:PORT/prt:PORT_LIST/prt:ifname {
        deviate add {
            sonic-ext:cascade-delete "enable";
        }
    }
}
