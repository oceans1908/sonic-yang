module openconfig-system-deviation {

    yang-version "1";

    // namespace
    namespace "http://openconfig.net/yang/system/deviation/extension";

    prefix "oc-sys-dev";

    // import some basic types
    import openconfig-system { prefix oc-sys; }
    import openconfig-extensions { prefix oc-ext; }
    import openconfig-system-ext { prefix oc-sys-ext; }

    organization
      "SONiC";

    contact
      "SONiC";

    description
      "This module describes a YANG model for openconfig-system deviations.";

    oc-ext:openconfig-version "0.1.2";

    revision "2024-02-29" {
      description
        "Add ARS feature deviations.";
      reference "0.1.2";
    }

    revision "2023-09-27" {
      description
        "Add ntp source address deviations.";
      reference "0.1.2";
    }

    revision "2023-09-08" {
      description
        "Add Yang extension for unsupported NTP state.";
      reference "0.1.1";
    }

    revision "2023-09-08" {
      description
        "Add Yang extension for unsupported NTP state.";
      reference "0.1.1";
    }

    revision "2021-06-16" {
      description
        "Add SONiC specific System deviations.";
      reference "0.1.0";
    }

    deviation /oc-sys:system/oc-sys:license {
      deviate not-supported;
    }

    deviation /oc-sys:system/oc-sys:telnet-server {
      deviate not-supported;
    }

    deviation /oc-sys:system/oc-sys:messages {
      deviate not-supported;
    }

    typedef intf-mode {
        type enumeration {
          enum STANDARD {
              description "Standard naming convention for physical interfaces will be represented as Eth[slot/port/breakout-port], where slot will start from 1 and port/breakout-port numbers will start from 1. Slot will always likely to be 1 in fixed pizza-box format, but may take different values in chassis format. This name format is fixed and will not have references to interface speed. For e.g Eth1/1 (in non breakout mode), Eth1/1/1 (in breakout mode)";
          }
          enum STANDARD_EXT {
              description "Standard extension naming convention for physical interfaces will be represented as Eth[slot/port/breakout-port], where slot will start from 1 and port/breakout-port numbers will start from 1. Slot will always likely to be 1 in fixed pizza-box format, but may take different values in chassis format. This name format is fixed and will not have references to interface speed. For e.g Eth1/1 (in non breakout mode), Eth1/1/1 (in breakout mode). Naming in database also changes";
          }
          enum NATIVE {
              description "Physical interfaces in Native mode will be of the format Ethernet0, Ethernet4 etc.,";
          }
        }
        description "Interface naming modes";
    }

    grouping system-deviation-attrs-config {
        description "Grouping System configuration attributes";

        leaf intf-naming-mode {
          type intf-mode;
          default "NATIVE";
          description "Interface naming mode";
        }

        leaf resource-stats-polling-interval {
            type uint32 {
                range "120..3600";
            }
            default 120;
            units "seconds";
            description "Polling interval to retrieve system resource utilization metrics like CPU, Memory etc., valid range is 120 to 3600";
        }
    }

    augment "/oc-sys:system/oc-sys:config" {
      description "Additional attributes for global system related configuration";

      uses system-deviation-attrs-config;
    }

    augment "/oc-sys:system/oc-sys:state" {
      description "Additional attributes for global system related operational state data";

      uses system-deviation-attrs-config;
    }

    deviation "/oc-sys:system/oc-sys:dns/oc-sys:host-entries" {
        deviate not-supported;
    }

    deviation /oc-sys:system/oc-sys:ntp/oc-sys:config/oc-sys:ntp-source-address {
        deviate not-supported;
    }

    deviation /oc-sys:system/oc-sys:ntp/oc-sys:state/oc-sys:ntp-source-address {
        deviate not-supported;
    }

    deviation /oc-sys:system/oc-sys:ntp/oc-sys:servers/oc-sys:server/oc-sys:config/oc-sys:port {
        deviate not-supported;
    }
    deviation /oc-sys:system/oc-sys:ntp/oc-sys:servers/oc-sys:server/oc-sys:config/oc-sys:version {
        deviate not-supported;
    }
    deviation /oc-sys:system/oc-sys:ntp/oc-sys:servers/oc-sys:server/oc-sys:config/oc-sys:association-type {
        deviate not-supported;
    }
    deviation /oc-sys:system/oc-sys:ntp/oc-sys:servers/oc-sys:server/oc-sys:config/oc-sys:iburst {
        deviate not-supported;
    }
    deviation /oc-sys:system/oc-sys:ntp/oc-sys:servers/oc-sys:server/oc-sys:state/oc-sys:root-delay {
        deviate not-supported;
    }
    deviation /oc-sys:system/oc-sys:ntp/oc-sys:servers/oc-sys:server/oc-sys:state/oc-sys:root-dispersion {
        deviate not-supported;
    }

    deviation /oc-sys:system/oc-sys:ntp/oc-sys:servers/oc-sys:server/oc-sys:state/oc-sys:port {
      deviate not-supported;
    }
    deviation /oc-sys:system/oc-sys:ntp/oc-sys:servers/oc-sys:server/oc-sys:state/oc-sys:version {
      deviate not-supported;
    }
    deviation /oc-sys:system/oc-sys:ntp/oc-sys:servers/oc-sys:server/oc-sys:state/oc-sys:association-type {
      deviate not-supported;
    }
    deviation /oc-sys:system/oc-sys:ntp/oc-sys:servers/oc-sys:server/oc-sys:state/oc-sys:iburst {
      deviate not-supported;
    }

    deviation /oc-sys:system/oc-sys:ntp/oc-sys:servers/oc-sys:server/oc-sys:state/oc-sys:offset {
      deviate not-supported;
    }

    deviation /oc-sys:system/oc-sys:aaa/oc-sys:authentication/oc-sys:admin-user {
        deviate not-supported;
    }

    deviation /oc-sys:system/oc-sys:aaa/oc-sys:authorization/oc-sys:config {
        deviate not-supported;
    }

    deviation /oc-sys:system/oc-sys:aaa/oc-sys:authorization/oc-sys:state {
        deviate not-supported;
    }

    deviation /oc-sys:system/oc-sys:aaa/oc-sys:authorization/oc-sys:events {
        deviate not-supported;
    }

    deviation /oc-sys:system/oc-sys:aaa/oc-sys:accounting {
        deviate not-supported;
    }

    deviation /oc-sys:system/oc-sys:aaa/oc-sys:server-groups/oc-sys:server-group/oc-sys:config/oc-sys:type {
        deviate not-supported;
    }

    deviation /oc-sys:system/oc-sys:aaa/oc-sys:server-groups/oc-sys:server-group/oc-sys:state/oc-sys:type {
        deviate not-supported;
    }

    deviation /oc-sys:system/oc-sys:aaa/oc-sys:server-groups/oc-sys:server-group/oc-sys:servers/oc-sys:server/oc-sys:state/oc-sys:connection-opens {
        deviate not-supported;
    }

    deviation /oc-sys:system/oc-sys:aaa/oc-sys:server-groups/oc-sys:server-group/oc-sys:servers/oc-sys:server/oc-sys:config/oc-sys:name {
        deviate not-supported;
    }

    deviation /oc-sys:system/oc-sys:aaa/oc-sys:server-groups/oc-sys:server-group/oc-sys:servers/oc-sys:server/oc-sys:state/oc-sys:name {
        deviate not-supported;
    }

    deviation /oc-sys:system/oc-sys:aaa/oc-sys:server-groups/oc-sys:server-group/oc-sys:servers/oc-sys:server/oc-sys:state/oc-sys:connection-closes {
        deviate not-supported;
    }

    deviation /oc-sys:system/oc-sys:aaa/oc-sys:server-groups/oc-sys:server-group/oc-sys:servers/oc-sys:server/oc-sys:state/oc-sys:connection-aborts {
        deviate not-supported;
    }

    deviation /oc-sys:system/oc-sys:aaa/oc-sys:server-groups/oc-sys:server-group/oc-sys:servers/oc-sys:server/oc-sys:state/oc-sys:connection-failures {
        deviate not-supported;
    }

    deviation /oc-sys:system/oc-sys:aaa/oc-sys:server-groups/oc-sys:server-group/oc-sys:servers/oc-sys:server/oc-sys:state/oc-sys:connection-timeouts {
        deviate not-supported;
    }

    deviation /oc-sys:system/oc-sys:aaa/oc-sys:server-groups/oc-sys:server-group/oc-sys:servers/oc-sys:server/oc-sys:state/oc-sys:messages-sent {
        deviate not-supported;
    }

    deviation /oc-sys:system/oc-sys:aaa/oc-sys:server-groups/oc-sys:server-group/oc-sys:servers/oc-sys:server/oc-sys:state/oc-sys:messages-received {
        deviate not-supported;
    }

    deviation /oc-sys:system/oc-sys:aaa/oc-sys:server-groups/oc-sys:server-group/oc-sys:servers/oc-sys:server/oc-sys:state/oc-sys:errors-received {
        deviate not-supported;
    }
    
    
    deviation /oc-sys:system/oc-sys:aaa/oc-sys:server-groups/oc-sys:server-group/oc-sys:servers/oc-sys:server/oc-sys:tacacs/oc-sys:config/oc-sys:source-address {
        deviate not-supported;
    }

    deviation /oc-sys:system/oc-sys:aaa/oc-sys:server-groups/oc-sys:server-group/oc-sys:servers/oc-sys:server/oc-sys:tacacs/oc-sys:state/oc-sys:source-address {
        deviate not-supported;
    }

    deviation /oc-sys:system/oc-sys:aaa/oc-sys:server-groups/oc-sys:server-group/oc-sys:servers/oc-sys:server/oc-sys:tacacs/oc-sys:config/oc-sys:secret-key-hashed {
        deviate not-supported;
    }

    deviation /oc-sys:system/oc-sys:aaa/oc-sys:server-groups/oc-sys:server-group/oc-sys:servers/oc-sys:server/oc-sys:tacacs/oc-sys:state/oc-sys:secret-key-hashed {
        deviate not-supported;
    }

    deviation /oc-sys:system/oc-sys:aaa/oc-sys:server-groups/oc-sys:server-group/oc-sys:servers/oc-sys:server/oc-sys:radius/oc-sys:config/oc-sys:source-address {
        deviate not-supported;
    }

    deviation /oc-sys:system/oc-sys:aaa/oc-sys:server-groups/oc-sys:server-group/oc-sys:servers/oc-sys:server/oc-sys:radius/oc-sys:state/oc-sys:source-address {
        deviate not-supported;
    }

    deviation /oc-sys:system/oc-sys:aaa/oc-sys:server-groups/oc-sys:server-group/oc-sys:servers/oc-sys:server/oc-sys:radius/oc-sys:config/oc-sys:secret-key-hashed {
        deviate not-supported;
    }

    deviation /oc-sys:system/oc-sys:aaa/oc-sys:server-groups/oc-sys:server-group/oc-sys:servers/oc-sys:server/oc-sys:radius/oc-sys:state/oc-sys:secret-key-hashed {
        deviate not-supported;
    }

    deviation /oc-sys:system/oc-sys:ntp/oc-sys:config/oc-sys:enabled {
        deviate not-supported;
    }

    deviation /oc-sys:system/oc-sys:ntp/oc-sys:state/oc-sys:enabled {
        deviate not-supported;
    }

    deviation /oc-sys:system/oc-sys:ntp/oc-sys:state/oc-sys:auth-mismatch {
        deviate not-supported;
    }

    deviation /oc-sys:system/oc-sys:cpus/oc-sys:cpu/oc-sys:state/oc-sys:total/oc-sys:min {
        deviate not-supported;
    }
    deviation /oc-sys:system/oc-sys:cpus/oc-sys:cpu/oc-sys:state/oc-sys:total/oc-sys:max {
        deviate not-supported;
    }
    deviation /oc-sys:system/oc-sys:cpus/oc-sys:cpu/oc-sys:state/oc-sys:total/oc-sys:min-time {
        deviate not-supported;
    }
    deviation /oc-sys:system/oc-sys:cpus/oc-sys:cpu/oc-sys:state/oc-sys:total/oc-sys:max-time {
        deviate not-supported;
    }
    deviation /oc-sys:system/oc-sys:cpus/oc-sys:cpu/oc-sys:state/oc-sys:user/oc-sys:min {
        deviate not-supported;
    }
    deviation /oc-sys:system/oc-sys:cpus/oc-sys:cpu/oc-sys:state/oc-sys:user/oc-sys:max {
        deviate not-supported;
    }
    deviation /oc-sys:system/oc-sys:cpus/oc-sys:cpu/oc-sys:state/oc-sys:user/oc-sys:min-time {
        deviate not-supported;
    }
    deviation /oc-sys:system/oc-sys:cpus/oc-sys:cpu/oc-sys:state/oc-sys:user/oc-sys:max-time {
        deviate not-supported;
    }
    deviation /oc-sys:system/oc-sys:cpus/oc-sys:cpu/oc-sys:state/oc-sys:kernel/oc-sys:min {
        deviate not-supported;
    }
    deviation /oc-sys:system/oc-sys:cpus/oc-sys:cpu/oc-sys:state/oc-sys:kernel/oc-sys:max {
        deviate not-supported;
    }
    deviation /oc-sys:system/oc-sys:cpus/oc-sys:cpu/oc-sys:state/oc-sys:kernel/oc-sys:min-time {
        deviate not-supported;
    }
    deviation /oc-sys:system/oc-sys:cpus/oc-sys:cpu/oc-sys:state/oc-sys:kernel/oc-sys:max-time {
        deviate not-supported;
    }
    deviation /oc-sys:system/oc-sys:cpus/oc-sys:cpu/oc-sys:state/oc-sys:idle/oc-sys:min {
        deviate not-supported;
    }
    deviation /oc-sys:system/oc-sys:cpus/oc-sys:cpu/oc-sys:state/oc-sys:idle/oc-sys:max {
        deviate not-supported;
    }
    deviation /oc-sys:system/oc-sys:cpus/oc-sys:cpu/oc-sys:state/oc-sys:idle/oc-sys:min-time {
        deviate not-supported;
    }
    deviation /oc-sys:system/oc-sys:cpus/oc-sys:cpu/oc-sys:state/oc-sys:idle/oc-sys:max-time {
        deviate not-supported;
    }
    deviation /oc-sys:system/oc-sys:cpus/oc-sys:cpu/oc-sys:state/oc-sys:nice {
        deviate not-supported;
    }
    deviation /oc-sys:system/oc-sys:cpus/oc-sys:cpu/oc-sys:state/oc-sys:wait {
        deviate not-supported;
    }
    deviation /oc-sys:system/oc-sys:cpus/oc-sys:cpu/oc-sys:state/oc-sys:hardware-interrupt {
        deviate not-supported;
    }
    deviation /oc-sys:system/oc-sys:cpus/oc-sys:cpu/oc-sys:state/oc-sys:software-interrupt {
        deviate not-supported;
    }

    deviation "/oc-sys:system/oc-sys:dns/oc-sys:servers/oc-sys:server/oc-sys:config/oc-sys:port" {
        deviate not-supported;
    }

    deviation "/oc-sys:system/oc-sys:dns/oc-sys:servers/oc-sys:server/oc-sys:state/oc-sys:port" {
        deviate not-supported;
    }

    deviation /oc-sys:system/oc-sys-ext:adaptive-routing-switching/oc-sys-ext:ars-profile/oc-sys-ext:profile/oc-sys-ext:config/oc-sys-ext:quant-band-0-min {
      deviate not-supported;
    }

    deviation /oc-sys:system/oc-sys-ext:adaptive-routing-switching/oc-sys-ext:ars-profile/oc-sys-ext:profile/oc-sys-ext:state/oc-sys-ext:quant-band-0-min {
      deviate not-supported;
    }

    deviation /oc-sys:system/oc-sys-ext:adaptive-routing-switching/oc-sys-ext:ars-profile/oc-sys-ext:profile/oc-sys-ext:config/oc-sys-ext:quant-band-0-max {
      deviate not-supported;
    }

    deviation /oc-sys:system/oc-sys-ext:adaptive-routing-switching/oc-sys-ext:ars-profile/oc-sys-ext:profile/oc-sys-ext:state/oc-sys-ext:quant-band-0-max {
      deviate not-supported;
    }

    deviation /oc-sys:system/oc-sys-ext:adaptive-routing-switching/oc-sys-ext:ars-profile/oc-sys-ext:profile/oc-sys-ext:config/oc-sys-ext:quant-band-1-min {
      deviate not-supported;
    }

    deviation /oc-sys:system/oc-sys-ext:adaptive-routing-switching/oc-sys-ext:ars-profile/oc-sys-ext:profile/oc-sys-ext:state/oc-sys-ext:quant-band-1-min {
      deviate not-supported;
    }

    deviation /oc-sys:system/oc-sys-ext:adaptive-routing-switching/oc-sys-ext:ars-profile/oc-sys-ext:profile/oc-sys-ext:config/oc-sys-ext:quant-band-1-max {
      deviate not-supported;
    }

    deviation /oc-sys:system/oc-sys-ext:adaptive-routing-switching/oc-sys-ext:ars-profile/oc-sys-ext:profile/oc-sys-ext:state/oc-sys-ext:quant-band-1-max {
      deviate not-supported;
    }

    deviation /oc-sys:system/oc-sys-ext:adaptive-routing-switching/oc-sys-ext:ars-profile/oc-sys-ext:profile/oc-sys-ext:config/oc-sys-ext:quant-band-2-min {
      deviate not-supported;
    }

    deviation /oc-sys:system/oc-sys-ext:adaptive-routing-switching/oc-sys-ext:ars-profile/oc-sys-ext:profile/oc-sys-ext:state/oc-sys-ext:quant-band-2-min {
      deviate not-supported;
    }

    deviation /oc-sys:system/oc-sys-ext:adaptive-routing-switching/oc-sys-ext:ars-profile/oc-sys-ext:profile/oc-sys-ext:config/oc-sys-ext:quant-band-2-max {
      deviate not-supported;
    }

    deviation /oc-sys:system/oc-sys-ext:adaptive-routing-switching/oc-sys-ext:ars-profile/oc-sys-ext:profile/oc-sys-ext:state/oc-sys-ext:quant-band-2-max {
      deviate not-supported;
    }

    deviation /oc-sys:system/oc-sys-ext:adaptive-routing-switching/oc-sys-ext:ars-profile/oc-sys-ext:profile/oc-sys-ext:config/oc-sys-ext:quant-band-3-min {
      deviate not-supported;
    }

    deviation /oc-sys:system/oc-sys-ext:adaptive-routing-switching/oc-sys-ext:ars-profile/oc-sys-ext:profile/oc-sys-ext:state/oc-sys-ext:quant-band-3-min {
      deviate not-supported;
    }

    deviation /oc-sys:system/oc-sys-ext:adaptive-routing-switching/oc-sys-ext:ars-profile/oc-sys-ext:profile/oc-sys-ext:config/oc-sys-ext:quant-band-3-max {
      deviate not-supported;
    }

    deviation /oc-sys:system/oc-sys-ext:adaptive-routing-switching/oc-sys-ext:ars-profile/oc-sys-ext:profile/oc-sys-ext:state/oc-sys-ext:quant-band-3-max {
      deviate not-supported;
    }

    deviation /oc-sys:system/oc-sys-ext:adaptive-routing-switching/oc-sys-ext:ars-profile/oc-sys-ext:profile/oc-sys-ext:config/oc-sys-ext:quant-band-4-min {
      deviate not-supported;
    }

    deviation /oc-sys:system/oc-sys-ext:adaptive-routing-switching/oc-sys-ext:ars-profile/oc-sys-ext:profile/oc-sys-ext:state/oc-sys-ext:quant-band-4-min {
      deviate not-supported;
    }

    deviation /oc-sys:system/oc-sys-ext:adaptive-routing-switching/oc-sys-ext:ars-profile/oc-sys-ext:profile/oc-sys-ext:config/oc-sys-ext:quant-band-4-max {
      deviate not-supported;
    }

    deviation /oc-sys:system/oc-sys-ext:adaptive-routing-switching/oc-sys-ext:ars-profile/oc-sys-ext:profile/oc-sys-ext:state/oc-sys-ext:quant-band-4-max {
      deviate not-supported;
    }

    deviation /oc-sys:system/oc-sys-ext:adaptive-routing-switching/oc-sys-ext:ars-profile/oc-sys-ext:profile/oc-sys-ext:config/oc-sys-ext:quant-band-5-min {
      deviate not-supported;
    }

    deviation /oc-sys:system/oc-sys-ext:adaptive-routing-switching/oc-sys-ext:ars-profile/oc-sys-ext:profile/oc-sys-ext:state/oc-sys-ext:quant-band-5-min {
      deviate not-supported;
    }

    deviation /oc-sys:system/oc-sys-ext:adaptive-routing-switching/oc-sys-ext:ars-profile/oc-sys-ext:profile/oc-sys-ext:config/oc-sys-ext:quant-band-5-max {
      deviate not-supported;
    }

    deviation /oc-sys:system/oc-sys-ext:adaptive-routing-switching/oc-sys-ext:ars-profile/oc-sys-ext:profile/oc-sys-ext:state/oc-sys-ext:quant-band-5-max {
      deviate not-supported;
    }

    deviation /oc-sys:system/oc-sys-ext:adaptive-routing-switching/oc-sys-ext:ars-profile/oc-sys-ext:profile/oc-sys-ext:config/oc-sys-ext:quant-band-6-min {
      deviate not-supported;
    }

    deviation /oc-sys:system/oc-sys-ext:adaptive-routing-switching/oc-sys-ext:ars-profile/oc-sys-ext:profile/oc-sys-ext:state/oc-sys-ext:quant-band-6-min {
      deviate not-supported;
    }

    deviation /oc-sys:system/oc-sys-ext:adaptive-routing-switching/oc-sys-ext:ars-profile/oc-sys-ext:profile/oc-sys-ext:config/oc-sys-ext:quant-band-6-max {
      deviate not-supported;
    }

    deviation /oc-sys:system/oc-sys-ext:adaptive-routing-switching/oc-sys-ext:ars-profile/oc-sys-ext:profile/oc-sys-ext:state/oc-sys-ext:quant-band-6-max {
      deviate not-supported;
    }

    deviation /oc-sys:system/oc-sys-ext:adaptive-routing-switching/oc-sys-ext:ars-profile/oc-sys-ext:profile/oc-sys-ext:config/oc-sys-ext:quant-band-7-min {
      deviate not-supported;
    }

    deviation /oc-sys:system/oc-sys-ext:adaptive-routing-switching/oc-sys-ext:ars-profile/oc-sys-ext:profile/oc-sys-ext:state/oc-sys-ext:quant-band-7-min {
      deviate not-supported;
    }

    deviation /oc-sys:system/oc-sys-ext:adaptive-routing-switching/oc-sys-ext:ars-profile/oc-sys-ext:profile/oc-sys-ext:config/oc-sys-ext:quant-band-7-max {
      deviate not-supported;
    }

    deviation /oc-sys:system/oc-sys-ext:adaptive-routing-switching/oc-sys-ext:ars-profile/oc-sys-ext:profile/oc-sys-ext:state/oc-sys-ext:quant-band-7-max {
      deviate not-supported;
    }

    deviation /oc-sys:system/oc-sys-ext:adaptive-routing-switching/oc-sys-ext:ars-port-profile/oc-sys-ext:portprofile/oc-sys-ext:config/oc-sys-ext:alt-path {
      deviate not-supported;
    }

    deviation /oc-sys:system/oc-sys-ext:adaptive-routing-switching/oc-sys-ext:ars-port-profile/oc-sys-ext:portprofile/oc-sys-ext:state/oc-sys-ext:alt-path {
      deviate not-supported;
    }    

    deviation /oc-sys:system/oc-sys-ext:adaptive-routing-switching/oc-sys-ext:ars-port-profile/oc-sys-ext:portprofile/oc-sys-ext:config/oc-sys-ext:load-past-enable {
      deviate not-supported;
    }

    deviation /oc-sys:system/oc-sys-ext:adaptive-routing-switching/oc-sys-ext:ars-port-profile/oc-sys-ext:portprofile/oc-sys-ext:state/oc-sys-ext:load-past-enable {
      deviate not-supported;
    }

    deviation /oc-sys:system/oc-sys-ext:adaptive-routing-switching/oc-sys-ext:ars-port-profile/oc-sys-ext:portprofile/oc-sys-ext:config/oc-sys-ext:load-future-enable {
      deviate not-supported;
    }

    deviation /oc-sys:system/oc-sys-ext:adaptive-routing-switching/oc-sys-ext:ars-port-profile/oc-sys-ext:portprofile/oc-sys-ext:state/oc-sys-ext:load-future-enable {
      deviate not-supported;
    }

    deviation /oc-sys:system/oc-sys-ext:adaptive-routing-switching/oc-sys-ext:ars-object/oc-sys-ext:arsobject/oc-sys-ext:config/oc-sys-ext:mon-enable {
      deviate not-supported;
    }

    deviation /oc-sys:system/oc-sys-ext:adaptive-routing-switching/oc-sys-ext:ars-object/oc-sys-ext:arsobject/oc-sys-ext:state/oc-sys-ext:mon-enable {
      deviate not-supported;
    } 

    deviation /oc-sys:system/oc-sys-ext:adaptive-routing-switching/oc-sys-ext:ars-object/oc-sys-ext:arsobject/oc-sys-ext:config/oc-sys-ext:sample-packet {
      deviate not-supported;
    }

    deviation /oc-sys:system/oc-sys-ext:adaptive-routing-switching/oc-sys-ext:ars-object/oc-sys-ext:arsobject/oc-sys-ext:state/oc-sys-ext:sample-packet {
      deviate not-supported;
    } 

    deviation /oc-sys:system/oc-sys-ext:adaptive-routing-switching/oc-sys-ext:ars-object/oc-sys-ext:arsobject/oc-sys-ext:config/oc-sys-ext:primary-path-quality-threshold {
      deviate not-supported;
    }

    deviation /oc-sys:system/oc-sys-ext:adaptive-routing-switching/oc-sys-ext:ars-object/oc-sys-ext:arsobject/oc-sys-ext:state/oc-sys-ext:primary-path-quality-threshold {
      deviate not-supported;
    } 

    deviation /oc-sys:system/oc-sys-ext:adaptive-routing-switching/oc-sys-ext:ars-object/oc-sys-ext:arsobject/oc-sys-ext:config/oc-sys-ext:alt-path {
      deviate not-supported;
    }

    deviation /oc-sys:system/oc-sys-ext:adaptive-routing-switching/oc-sys-ext:ars-object/oc-sys-ext:arsobject/oc-sys-ext:state/oc-sys-ext:alt-path {
      deviate not-supported;
    } 

    deviation /oc-sys:system/oc-sys-ext:adaptive-routing-switching/oc-sys-ext:ars-object/oc-sys-ext:arsobject/oc-sys-ext:config/oc-sys-ext:alt-path-cost {
      deviate not-supported;
    }

    deviation /oc-sys:system/oc-sys-ext:adaptive-routing-switching/oc-sys-ext:ars-object/oc-sys-ext:arsobject/oc-sys-ext:state/oc-sys-ext:alt-path-cost {
      deviate not-supported;
    } 

    deviation /oc-sys:system/oc-sys-ext:adaptive-routing-switching/oc-sys-ext:ars-object/oc-sys-ext:arsobject/oc-sys-ext:config/oc-sys-ext:alt-path-bias {
      deviate not-supported;
    }

    deviation /oc-sys:system/oc-sys-ext:adaptive-routing-switching/oc-sys-ext:ars-object/oc-sys-ext:arsobject/oc-sys-ext:state/oc-sys-ext:alt-path-bias {
      deviate not-supported;
    } 

    deviation /oc-sys:system/oc-sys-ext:adaptive-routing-switching/oc-sys-ext:ars-object/oc-sys-ext:arsobject/oc-sys-ext:config/oc-sys-ext:max-primary-members {
      deviate not-supported;
    }

    deviation /oc-sys:system/oc-sys-ext:adaptive-routing-switching/oc-sys-ext:ars-object/oc-sys-ext:arsobject/oc-sys-ext:state/oc-sys-ext:max-primary-members {
      deviate not-supported;
    } 

    deviation /oc-sys:system/oc-sys-ext:adaptive-routing-switching/oc-sys-ext:ars-object/oc-sys-ext:arsobject/oc-sys-ext:config/oc-sys-ext:max-alt-members {
      deviate not-supported;
    }

    deviation /oc-sys:system/oc-sys-ext:adaptive-routing-switching/oc-sys-ext:ars-object/oc-sys-ext:arsobject/oc-sys-ext:state/oc-sys-ext:max-alt-members {
      deviate not-supported;
    }                      
}
