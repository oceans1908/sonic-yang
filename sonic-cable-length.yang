module sonic-cable-length {

    yang-version 1.1;

    namespace  "http://github.com/Azure/sonic-cable-length";

    prefix cable-length;

    import sonic-port {
        prefix prt;
    }

	import sonic-extension {
		prefix sonic-ext;
	}
    
	organization
		"SONiC";

	contact
		"SONiC";

    description "CABLE_LENGTH YANG module for SONiC OS";

    revision 2021-11-11 {
        description "Initial version";
    }

    container sonic-cable-length {
        container CABLE_LENGTH {

            description "CABLE_LENGTH part of config_db.json";

            list CABLE_LENGTH_LIST {
                key "name";
                sonic-ext:custom-validation ValidateBufferConfigsInitilized;
                sonic-ext:custom-validation ValidateModifyOnlyAttr;

                leaf name {
                    type string {
                        pattern '[a-zA-Z0-9]{1}([-a-zA-Z0-9_]{0,31})' {
                            error-message "Invalid cable length list name.";
                            error-app-tag cable-length-invalid-list-name;
                        }
                        length 1..32 {
                            error-message "Invalid length for the cable length list name.";
                            error-app-tag cable-length-invalid-list-name-length;
                        }
                    }
                }

                list CABLE_LENGTH {
                    key "port";

                    leaf port {
                        type leafref {
	                        path "/prt:sonic-port/prt:PORT/prt:PORT_LIST/prt:ifname";
                        }
                    }

                    leaf length {
                        type string {
                            pattern '5m|40m|300m' {
                                error-message "Invalid cable length.";
                                error-app-tag cable-length-invalid-length;
                            }
                        }
                    }
                }
            }
        }
    }
}
