module sonic-fdb {
    namespace "http://github.com/Azure/sonic-fdb";
    prefix sfdb;
    yang-version 1.1;

    import ietf-yang-types {
        prefix yang;
    }

    import sonic-port {
        prefix prt;
    }

    import sonic-portchannel {
        prefix spc;
    }

    import sonic-extension {
        prefix sonic-ext;
    }

    organization
        "SONiC";

    contact
        "SONiC";

    description
        "SONIC FDB";

    revision 2023-01-12 {
        description
            "Added custom-validation for MAC-address.";
    }

    revision 2020-07-15 {
        description
            "Adding union for leaf port.";
    }

    revision 2019-11-07 {
        description
            "Adding RPC for clear FDB.";
    }

    revision 2019-10-10 {
        description
            "Initial revision.";
    }

    rpc clear_fdb {
        input {
            leaf mac-param {
                type string;
                    description
                        "parameter for deleting either all dynamic mac address or a record related to interface name / vlan id.
                            Options can be specified as VLAN:<vlan-id>, VLAN_MAC:<vlanid>|<mac-address> or PORT:<interface-name>";
                }
        }
        output {
            leaf status {
                type string;
                    description
                        " success / failure of deletion of dynamic mac address";
            }
        }
    }

    rpc clear_fdb_sticky {
        input {
            leaf mac-param {
                type string;
                    description
                        "parameter for deleting either all sticky mac addresses or sticky mac addresses related to interface name / vlan id.
                            Options can be specified as VLAN:<vlan-id>, VLAN_MAC:<vlanid>|<mac-address> or PORT:<interface-name>";
                }
        }
        output {
            leaf status {
                type string;
                    description
                        " success / failure of deletion of sticky mac addresses";
            }
        }
    }

    container sonic-fdb {

        container FDB {

            list FDB_LIST {
                key "vlan mac-address";

                leaf vlan {
                    type string {
                        pattern "Vlan(409[0-5]|40[0-8][0-9]|[1-3][0-9]{3}|[1-9][0-9]{2}|[1-9][0-9]|[1-9])" {
                        error-message "Invalid Vlan name pattern";
                        error-app-tag vlan-name-invalid;
                        }    
                    }
	        }

                leaf mac-address {
                    type yang:mac-address;
                    sonic-ext:custom-validation ValidateFdbMacAddress;
                    description
                        "MAC address for the dynamic or static MAC table entry";
                }

                leaf port{
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf type {
                    type string;
                    description
                        "Statically or dynamically programmed MAC table entry";
                }
	    }
	}
    }
}
